CLAB-WIFI-MIB DEFINITIONS ::= BEGIN
IMPORTS 
    MODULE-IDENTITY, 
    OBJECT-TYPE, 
    NOTIFICATION-TYPE,
    enterprises,
    Unsigned32,
    Integer32,
    Counter32,
    Counter64
                       FROM SNMPv2-SMI 
    OBJECT-GROUP, 
    MODULE-COMPLIANCE,
    NOTIFICATION-GROUP 
                       FROM SNMPv2-CONF 
    SnmpAdminString 
                       FROM SNMP-FRAMEWORK-MIB 
     
    MacAddress,
    DateAndTime,
    TruthValue,
    RowStatus 
                       FROM SNMPv2-TC
    
    InetAddressType,
    InetAddress,
    InetPortNumber
     
                       FROM INET-ADDRESS-MIB
    InterfaceIndex 
                       FROM IF-MIB;
    
		clabWIFIMib MODULE-IDENTITY

    LAST-UPDATED  "201009270000Z" -- Sept 27, 2010
	
    ORGANIZATION "Cable Television Laboratories, Inc." 
    CONTACT-INFO 
            "Broadband Network Services
             Cable Television Laboratories, Inc.
             858 Coal Creek Circle,
             Louisville, CO 80027, USA 
             Phone: +1 303-661-9100
             Email: mibs@cablelabs.com"
     DESCRIPTION 
            "Revised Version includes ECN
             WiFi-MGMT-N-10.00002-4
             and published as part of WR-SP-WiFi-MGMT-I02-101005" 
     REVISION "201009270000Z" -- Sept 27, 2010
     DESCRIPTION 
            "This MIB module contains the management objects
             for the Wi-Fi interface." 
     REVISION "201007290000Z" -- July 29, 2010
     DESCRIPTION
             "Initial version, published as part of the CableLabs
             Wi-Fi Provisioning Framework Specification
             WR-SP-WiFi-MGMT-I01-100729
             Copyright 2010 Cable Television Laboratories, Inc.
             All rights reserved."   
             
    
    ::= { enterprises 4491 5 1 }
	

-- Textual Conventions

-- Object Definitions
clabWIFINotifications OBJECT IDENTIFIER ::= { clabWIFIMib 0 }
clabWIFIObjects OBJECT IDENTIFIER ::= { clabWIFIMib 1 }

clabWIFIWiFi OBJECT IDENTIFIER ::= {clabWIFIObjects 1 }

clabWIFIWiFiRadioNumberOfEntries    OBJECT-TYPE
    SYNTAX      Unsigned32 
    MAX-ACCESS  read-only
    STATUS      current
    DESCRIPTION
        "This object is defined in TR-181 Device.WiFi.RadioNumberOfEntries."
    REFERENCE
    		"TR-181 Device Data Model for TR-069."
    ::= {clabWIFIWiFi 1 }

clabWIFIWiFiSSIDNumberOfEntries    OBJECT-TYPE
    SYNTAX      Unsigned32 
    MAX-ACCESS  read-only
    STATUS      current
    DESCRIPTION
        "This object is defined in TR-181 Device.WiFi.SSIDNumberOfEntries."
    REFERENCE
    		"TR-181 Device Data Model for TR-069."
    ::= {clabWIFIWiFi 2 }

clabWIFIWiFiAccessPointNumberOfEntries    OBJECT-TYPE
    SYNTAX      Unsigned32 
    MAX-ACCESS  read-only
    STATUS      current
    DESCRIPTION
        "This object is defined in TR-181 Device.WiFi.AccessPointNumberOfEntries."
    REFERENCE
    		"TR-181 Device Data Model for TR-069."
    ::= {clabWIFIWiFi 3 }

clabWIFIWiFiEndPointNumberOfEntries    OBJECT-TYPE
    SYNTAX      Unsigned32 
    MAX-ACCESS  read-only
    STATUS      current
    DESCRIPTION
        "This object is defined in TR-181 Device.WiFi.EndPointNumberOfEntries."
    REFERENCE
    		"TR-181 Device Data Model for TR-069."
    ::= {clabWIFIWiFi 4 }

clabWIFIRadioTable OBJECT-TYPE
    SYNTAX      SEQUENCE OF ClabWIFIRadioEntry
    MAX-ACCESS  not-accessible
    STATUS      current
    DESCRIPTION
        "This object is defined in TR-181 Device.WiFi.Radio"
    REFERENCE
    		"TR-181 Device Data Model for TR-069."
    ::= {clabWIFIObjects 2 }

clabWIFIRadioEntry    OBJECT-TYPE
    SYNTAX      ClabWIFIRadioEntry
    MAX-ACCESS  not-accessible
    STATUS      current
    DESCRIPTION
        "The Conceptual row of clabWIFIRadioTable."
    INDEX {
            clabWIFIRadioId
          }
    ::= {clabWIFIRadioTable 1 }

ClabWIFIRadioEntry ::= SEQUENCE {
    clabWIFIRadioId
                 InterfaceIndex,
    clabWIFIRadioEnable
                 TruthValue,
    clabWIFIRadioStatus
                 INTEGER,
    clabWIFIRadioAlias
                 SnmpAdminString,
    clabWIFIRadioName
                 SnmpAdminString,
    clabWIFIRadioLastChange
                 Unsigned32,
    clabWIFIRadioLowerLayers
                 SnmpAdminString,
    clabWIFIRadioUpstream
                 TruthValue,
    clabWIFIRadioMaxBitRate
                 Unsigned32,
    clabWIFIRadioSupportedFrequencyBands
                 SnmpAdminString,
    clabWIFIRadioOperatingFrequencyBand
                 INTEGER,
    clabWIFIRadioSupportedStandards
                 SnmpAdminString,
    clabWIFIRadioOperatingStandards
                 INTEGER,
    clabWIFIRadioPossibleChannels
                 SnmpAdminString,
    clabWIFIRadioChannelsInUse
                 SnmpAdminString,
    clabWIFIRadioChannel
                 Unsigned32,
    clabWIFIRadioAutoChannelSupported
                 TruthValue,
    clabWIFIRadioAutoChannelEnable
                 TruthValue,
    clabWIFIRadioAutoChannelRefreshPeriod
                 Unsigned32,
    clabWIFIRadioOperatingChannelBandwidth
                 INTEGER,
    clabWIFIRadioExtensionChannel
                 INTEGER,
    clabWIFIRadioGuardInterval
                 INTEGER,
    clabWIFIRadioMCS
                 Integer32,
    clabWIFIRadioTransmitPowerSupported
                 SnmpAdminString,
    clabWIFIRadioTransmitPower
                 Unsigned32,
    clabWIFIRadioIEEE80211hSupported
                 TruthValue,
    clabWIFIRadioIEEE80211hEnabled
                 TruthValue,
    clabWIFIRadioRegulatoryDomain
                 SnmpAdminString
      }

clabWIFIRadioId    OBJECT-TYPE
    SYNTAX      InterfaceIndex 
    MAX-ACCESS  not-accessible
    STATUS      current
    DESCRIPTION
        "The key for a unique instance of this object. 
        This value corresponds to the Interface Index 
        (i.e., ifIndex in SMIv2). "
    ::= {clabWIFIRadioEntry 1 }

clabWIFIRadioEnable    OBJECT-TYPE
    SYNTAX      TruthValue 
    MAX-ACCESS  read-write
    STATUS      current
    DESCRIPTION
        "This object is defined in TR-181 Device.WiFi.Radio.{i}.Enable"
    REFERENCE
    		"TR-181 Device Data Model for TR-069."
    ::= {clabWIFIRadioEntry 2 }

clabWIFIRadioStatus    OBJECT-TYPE
    SYNTAX      INTEGER  {
                           up(1),
                           down(2),
                           unknown(4),
                           dormant(5),
                           notPresent(6),
                           lowerLayerDown(7),
                           error(8)
                         }
    MAX-ACCESS  read-only
    STATUS      current
    DESCRIPTION
        "This object is defined in TR-181 Device.WiFi.Radio.{i}.Status."
    REFERENCE
    		"TR-181 Device Data Model for TR-069."
    ::= {clabWIFIRadioEntry 3 }

clabWIFIRadioAlias    OBJECT-TYPE
    SYNTAX      SnmpAdminString (SIZE(0..64))
    MAX-ACCESS  read-write
    STATUS      current
    DESCRIPTION
        "This object is defined in TR-181 Device.WiFi.Radio.{i}.Alias."
    REFERENCE
    		"TR-181 Device Data Model for TR-069."
    ::= {clabWIFIRadioEntry 4 }

clabWIFIRadioName    OBJECT-TYPE
    SYNTAX      SnmpAdminString (SIZE(0..64))
    MAX-ACCESS  read-only
    STATUS      current
    DESCRIPTION
        "This object is defined in TR-181 Device.WiFi.Radio.{i}.Name."
    REFERENCE
    		"TR-181 Device Data Model for TR-069."
    ::= {clabWIFIRadioEntry 5 }

clabWIFIRadioLastChange    OBJECT-TYPE
    SYNTAX      Unsigned32 
    UNITS       "seconds"
    MAX-ACCESS  read-only
    STATUS      current
    DESCRIPTION
        "This object is defined in TR-181 Device.WiFi.Radio.{i}.LastChange."
    REFERENCE
    		"TR-181 Device Data Model for TR-069."
    ::= {clabWIFIRadioEntry 6 }

clabWIFIRadioLowerLayers    OBJECT-TYPE
    SYNTAX      SnmpAdminString (SIZE(0..1024))
    MAX-ACCESS  read-write
    STATUS      current
    DESCRIPTION
        "This object is defined in TR-181 Device.WiFi.Radio.{i}.LowerLayers."
    REFERENCE
    		"TR-181 Device Data Model for TR-069."
    ::= {clabWIFIRadioEntry 7 }

clabWIFIRadioUpstream    OBJECT-TYPE
    SYNTAX      TruthValue 
    MAX-ACCESS  read-only
    STATUS      current
    DESCRIPTION
        "This object is defined in TR-181 Device.WiFi.Radio.{i}.Upstream"
    REFERENCE
    		"TR-181 Device Data Model for TR-069."
    ::= {clabWIFIRadioEntry 8 }

clabWIFIRadioMaxBitRate    OBJECT-TYPE
    SYNTAX      Unsigned32 
    UNITS       "Mbps"
    MAX-ACCESS  read-only
    STATUS      current
    DESCRIPTION
        "This object is defined in TR-181 Device.WiFi.Radio.{i}.MaxBitRate."
    REFERENCE
    		"TR-181 Device Data Model for TR-069."
    ::= {clabWIFIRadioEntry 9 }

clabWIFIRadioSupportedFrequencyBands    OBJECT-TYPE
    SYNTAX      SnmpAdminString
    MAX-ACCESS  read-only
    STATUS      current
    DESCRIPTION
        "This object is defined in TR-181 Device.WiFi.RadioSupportedFrequencyBands."
    REFERENCE
    		"TR-181 Device Data Model for TR-069."
    ::= {clabWIFIRadioEntry 10 }

clabWIFIRadioOperatingFrequencyBand    OBJECT-TYPE
    SYNTAX      INTEGER  {
                           n2dot4Ghz(1),
                           n5Ghz(2)
                         }
    MAX-ACCESS  read-write
    STATUS      current
    DESCRIPTION
        "This object is defined in TR-181 Device.WiFi.Radio.{i}.OperatingFrequencyBand"
    REFERENCE
    		"TR-181 Device Data Model for TR-069."
    ::= {clabWIFIRadioEntry 11 }

clabWIFIRadioSupportedStandards    OBJECT-TYPE
    SYNTAX      SnmpAdminString
    MAX-ACCESS  read-only
    STATUS      current
    DESCRIPTION
        "This object is defined in TR-181 Device.WiFi.Radio.{i}.SupportedStandards"
    REFERENCE
    		"TR-181 Device Data Model for TR-069."
    ::= {clabWIFIRadioEntry 12 }

clabWIFIRadioOperatingStandards    OBJECT-TYPE
    SYNTAX      INTEGER  {
                           a(1),
                           b(2),
                           g(3),
                           n(5)
                         }
    MAX-ACCESS  read-write
    STATUS      current
    DESCRIPTION
        "This object is defined in TR-181 Device.WiFi.Radio.{i}.OperatingStandards"
    REFERENCE
    		"TR-181 Device Data Model for TR-069."
    ::= {clabWIFIRadioEntry 13 }

clabWIFIRadioPossibleChannels    OBJECT-TYPE
    SYNTAX      SnmpAdminString (SIZE(0..1024))
    MAX-ACCESS  read-only
    STATUS      current
    DESCRIPTION
        "This object is defined in TR-181 Device.WiFi.Radio.{i}.PossibleChannels"
    REFERENCE
    		"TR-181 Device Data Model for TR-069."
    ::= {clabWIFIRadioEntry 14 }

clabWIFIRadioChannelsInUse    OBJECT-TYPE
    SYNTAX      SnmpAdminString (SIZE(0..1024))
    MAX-ACCESS  read-only
    STATUS      current
    DESCRIPTION
        "This object is defined in TR-181 Device.WiFi.Radio.{i}.ChannelsInUse"
    REFERENCE
    		"TR-181 Device Data Model for TR-069."
    ::= {clabWIFIRadioEntry 15 }

clabWIFIRadioChannel    OBJECT-TYPE
    SYNTAX      Unsigned32 (1..255)
    MAX-ACCESS  read-write
    STATUS      current
    DESCRIPTION
        "This object is defined in TR-181 Device.WiFi.Radio.{i}.Channel"
    REFERENCE
    		"TR-181 Device Data Model for TR-069."
    ::= {clabWIFIRadioEntry 16 }

clabWIFIRadioAutoChannelSupported    OBJECT-TYPE
    SYNTAX      TruthValue 
    MAX-ACCESS  read-only
    STATUS      current
    DESCRIPTION
        "This object is defined in TR-181 Device.WiFi.Radio.{i}.AutoChannelSupported"
    REFERENCE
    		"TR-181 Device Data Model for TR-069."
    ::= {clabWIFIRadioEntry 17 }

clabWIFIRadioAutoChannelEnable    OBJECT-TYPE
    SYNTAX      TruthValue 
    MAX-ACCESS  read-write
    STATUS      current
    DESCRIPTION
        "This object is defined in TR-181 Device.WiFi.Radio.{i}.AutoChannelEnable"
    REFERENCE
    		"TR-181 Device Data Model for TR-069."
    ::= {clabWIFIRadioEntry 18 }

clabWIFIRadioAutoChannelRefreshPeriod    OBJECT-TYPE
    SYNTAX      Unsigned32 
    UNITS       "seconds"
    MAX-ACCESS  read-write
    STATUS      current
    DESCRIPTION
        "This object is defined in TR-181 Device.WiFi.Radio.{i}.AutoChannelRefreshPeriod"
    REFERENCE
    		"TR-181 Device Data Model for TR-069."
    ::= {clabWIFIRadioEntry 19 }

clabWIFIRadioOperatingChannelBandwidth    OBJECT-TYPE
    SYNTAX      INTEGER  {
                           n20Hhz(1),
                           n40Mhz(2),
                           auto(3)
                         }
    MAX-ACCESS  read-write
    STATUS      current
    DESCRIPTION
        "This object is defined in TR-181 Device.WiFi.Radio.{i}.OperatingChannelBandwidth"
    REFERENCE
    		"TR-181 Device Data Model for TR-069."
    DEFVAL      { auto }
    ::= {clabWIFIRadioEntry 20 }

clabWIFIRadioExtensionChannel    OBJECT-TYPE
    SYNTAX      INTEGER  {
                           aboveControlChannel(1),
                           belowControlChannel(2),
                           auto(3)
                         } 
    MAX-ACCESS  read-write
    STATUS      current
    DESCRIPTION
        "This object is defined in TR-181 Device.WiFi.Radio.{i}.ExtensionChannel"
    REFERENCE
    		"TR-181 Device Data Model for TR-069."
    DEFVAL      { auto }
    ::= {clabWIFIRadioEntry 21 }

clabWIFIRadioGuardInterval    OBJECT-TYPE
    SYNTAX      INTEGER  {
                           n400nsec(1),
                           n800nsec(2),
                           auto(3)
                         }  
    MAX-ACCESS  read-write
    STATUS      current
    DESCRIPTION
        "This object is defined in TR-181 Device.WiFi.Radio.{i}.RadioGuardInterval"
    REFERENCE
    		"TR-181 Device Data Model for TR-069."
    DEFVAL      { auto }
    ::= {clabWIFIRadioEntry 22 }

clabWIFIRadioMCS    OBJECT-TYPE
    SYNTAX      Integer32 (-1..31)
    MAX-ACCESS  read-write
    STATUS      current
    DESCRIPTION
        "This object is defined in TR-181 Device.WiFi.Radio.{i}.RadioMCS "
    REFERENCE
    		"TR-181 Device Data Model for TR-069."
    ::= {clabWIFIRadioEntry 23 }

clabWIFIRadioTransmitPowerSupported    OBJECT-TYPE
    SYNTAX      SnmpAdminString (SIZE(0..64))
    MAX-ACCESS  read-only
    STATUS      current
    DESCRIPTION
        "This object is defined in TR-181 Device.WiFi.Radio.{i}.TransmitPowerSupported"
    REFERENCE
    		"TR-181 Device Data Model for TR-069."
    ::= {clabWIFIRadioEntry 24 }

clabWIFIRadioTransmitPower    OBJECT-TYPE
    SYNTAX      Unsigned32 (1..100)
    UNITS       "percentage"
    MAX-ACCESS  read-write
    STATUS      current
    DESCRIPTION
        "This object is defined in TR-181 Device.WiFi.Radio.{i}.TransmitPower"
    REFERENCE
    		"TR-181 Device Data Model for TR-069."
    ::= {clabWIFIRadioEntry 25 }

clabWIFIRadioIEEE80211hSupported    OBJECT-TYPE
    SYNTAX      TruthValue 
    MAX-ACCESS  read-only
    STATUS      current
    DESCRIPTION
        "This object is defined in TR-181 Device.WiFi.Radio.{i}.IEEE80211hSupported"
    REFERENCE
    		"TR-181 Device Data Model for TR-069."
    ::= {clabWIFIRadioEntry 26 }

clabWIFIRadioIEEE80211hEnabled    OBJECT-TYPE
    SYNTAX      TruthValue 
    MAX-ACCESS  read-write
    STATUS      current
    DESCRIPTION
        "This object is defined in TR-181 Device.WiFi.Radio.{i}.IEEE80211hEnabled"
    REFERENCE
    		"TR-181 Device Data Model for TR-069."
    ::= {clabWIFIRadioEntry 27 }

clabWIFIRadioRegulatoryDomain    OBJECT-TYPE
    SYNTAX      SnmpAdminString 
    MAX-ACCESS  read-write
    STATUS      current
    DESCRIPTION
        "This object is defined in TR-181 Device.WiFi.Radio.{i}.RegulatoryDomain"
    REFERENCE
    		"TR-181 Device Data Model for TR-069."
    ::= {clabWIFIRadioEntry 28 }

clabWIFIRadioStatsTable OBJECT-TYPE
    SYNTAX      SEQUENCE OF ClabWIFIRadioStatsEntry
    MAX-ACCESS  not-accessible
    STATUS      current
    DESCRIPTION
        "This object is defined in TR-181 Device.WiFi.Radio.{i}.Stats."
    REFERENCE
    		"TR-181 Device Data Model for TR-069."
    ::= {clabWIFIObjects 3 }

clabWIFIRadioStatsEntry    OBJECT-TYPE
    SYNTAX      ClabWIFIRadioStatsEntry
    MAX-ACCESS  not-accessible
    STATUS      current
    DESCRIPTION
        "The Conceptual row of clabWIFIRadioStatsTable."
    REFERENCE
        "TR-181 Issue 2"
    INDEX {
            clabWIFIRadioId
          }
    ::= {clabWIFIRadioStatsTable 1 }

ClabWIFIRadioStatsEntry ::= SEQUENCE {
    clabWIFIRadioStatsBytesSent
                 Counter64,
    clabWIFIRadioStatsBytesReceived
                 Counter64,
    clabWIFIRadioStatsPacketsSent
                 Counter64,
    clabWIFIRadioStatsPacketsReceived
                 Counter64,
    clabWIFIRadioStatsErrorsSent
                 Counter32,
    clabWIFIRadioStatsErrorsReceived
                 Counter32,
    clabWIFIRadioStatsDiscardPacketsSent
                 Counter32,
    clabWIFIRadioStatsDiscardPacketsReceived
                 Counter32
      }

clabWIFIRadioStatsBytesSent    OBJECT-TYPE
    SYNTAX      Counter64 
    MAX-ACCESS  read-only
    STATUS      current
    DESCRIPTION
        "This object is defined in TR-181 Device.WiFi.Radio.{i}.Stats.BytesSent."
    REFERENCE
    		"TR-181 Device Data Model for TR-069."
    ::= {clabWIFIRadioStatsEntry 1 }

clabWIFIRadioStatsBytesReceived    OBJECT-TYPE
    SYNTAX      Counter64 
    MAX-ACCESS  read-only
    STATUS      current
    DESCRIPTION
        "This object is defined in TR-181 Device.WiFi.Radio.{i}.Stats.BytesReceived."
    REFERENCE
    		"TR-181 Device Data Model for TR-069."
    ::= {clabWIFIRadioStatsEntry 2 }

clabWIFIRadioStatsPacketsSent    OBJECT-TYPE
    SYNTAX      Counter64 
    MAX-ACCESS  read-only
    STATUS      current
    DESCRIPTION
        "This object is defined in TR-181 Device.WiFi.Radio.{i}.Stats.PacketsSent."
    REFERENCE
    		"TR-181 Device Data Model for TR-069."
    ::= {clabWIFIRadioStatsEntry 3 }

clabWIFIRadioStatsPacketsReceived    OBJECT-TYPE
    SYNTAX      Counter64 
    MAX-ACCESS  read-only
    STATUS      current
    DESCRIPTION
        "This object is defined in TR-181 Device.WiFi.Radio.{i}.Stats.PacketsReceived."
    REFERENCE
    		"TR-181 Device Data Model for TR-069."
    ::= {clabWIFIRadioStatsEntry 4 }

clabWIFIRadioStatsErrorsSent    OBJECT-TYPE
    SYNTAX      Counter32 
    MAX-ACCESS  read-only
    STATUS      current
    DESCRIPTION
        "This object is defined in TR-181 Device.WiFi.Radio.{i}.Stats.ErrorsSent."
    REFERENCE
    		"TR-181 Device Data Model for TR-069."
    ::= {clabWIFIRadioStatsEntry 5 }

clabWIFIRadioStatsErrorsReceived    OBJECT-TYPE
    SYNTAX      Counter32 
    MAX-ACCESS  read-only
    STATUS      current
    DESCRIPTION
        "This object is defined in TR-181 Device.WiFi.Radio.{i}.Stats.ErrorsReceived."
    REFERENCE
    		"TR-181 Device Data Model for TR-069."
    ::= {clabWIFIRadioStatsEntry 6 }

clabWIFIRadioStatsDiscardPacketsSent    OBJECT-TYPE
    SYNTAX      Counter32 
    MAX-ACCESS  read-only
    STATUS      current
    DESCRIPTION
        "This object is defined in TR-181 Device.WiFi.Radio.{i}.Stats.DiscardPacketsSent."
    REFERENCE
    		"TR-181 Device Data Model for TR-069."
    ::= {clabWIFIRadioStatsEntry 7 }

clabWIFIRadioStatsDiscardPacketsReceived    OBJECT-TYPE
    SYNTAX      Counter32 
    MAX-ACCESS  read-only
    STATUS      current
    DESCRIPTION
        "This object is defined in TR-181 Device.WiFi.Radio.{i}.Stats.DiscardPacketsReceived."
    REFERENCE
    		"TR-181 Device Data Model for TR-069."
    ::= {clabWIFIRadioStatsEntry 8 }

clabWIFISSIDTable OBJECT-TYPE
    SYNTAX      SEQUENCE OF ClabWIFISSIDEntry
    MAX-ACCESS  not-accessible
    STATUS      current
    DESCRIPTION
        "This object is defined in TR-181 Device.WiFi.SSID{i}."
    REFERENCE
    		"TR-181 Device Data Model for TR-069."
    ::= {clabWIFIObjects 4 }

clabWIFISSIDEntry    OBJECT-TYPE
    SYNTAX      ClabWIFISSIDEntry
    MAX-ACCESS  not-accessible
    STATUS      current
    DESCRIPTION
        "The Conceptual row of clabWIFISSIDTable."
    INDEX {
            clabWIFISSIDId
          }
    ::= {clabWIFISSIDTable 1 }

ClabWIFISSIDEntry ::= SEQUENCE {
    clabWIFISSIDId
                 InterfaceIndex,
    clabWIFISSIDEnable
                 TruthValue,
    clabWIFISSIDStatus
                 INTEGER,
    clabWIFISSIDAlias
                 SnmpAdminString,
    clabWIFISSIDName
                 SnmpAdminString,
    clabWIFISSIDLastChange
                 Unsigned32,
    clabWIFISSIDLowerLayers
                 SnmpAdminString,
    clabWIFISSIDBSSID
                 MacAddress,
    clabWIFISSIDMACAddress
                 MacAddress,
    clabWIFISSIDSSID
                 SnmpAdminString,
    clabWIFISSIDRowStatus
                 RowStatus
      }

clabWIFISSIDId    OBJECT-TYPE
    SYNTAX      InterfaceIndex 
    MAX-ACCESS  not-accessible
    STATUS      current
    DESCRIPTION
        "The key for a unique instance of this object. 
        This value corresponds to the Interface Index 
        (i.e., ifIndex in SMIv2). "
    ::= {clabWIFISSIDEntry 1 }

clabWIFISSIDEnable    OBJECT-TYPE
    SYNTAX      TruthValue 
    MAX-ACCESS  read-create
    STATUS      current
    DESCRIPTION
        "This object is defined in TR-181 Device.WiFi.SSID{i}.Enable."
    REFERENCE
    		"TR-181 Device Data Model for TR-069."
    ::= {clabWIFISSIDEntry 2 }

clabWIFISSIDStatus    OBJECT-TYPE
    SYNTAX      INTEGER  {
                           up(1),
                           down(2),
                           unknown(4),
                           dormant(5),
                           notPresent(6),
                           lowerLayerDown(7),
                           error(8)
                         }
    MAX-ACCESS  read-only
    STATUS      current
    DESCRIPTION
        "This object is defined in TR-181 Device.WiFi.SSID{i}.Status."
    REFERENCE
    		"TR-181 Device Data Model for TR-069."
    ::= {clabWIFISSIDEntry 3 }

clabWIFISSIDAlias    OBJECT-TYPE
    SYNTAX      SnmpAdminString (SIZE(0..64)) 
    MAX-ACCESS  read-create
    STATUS      current
    DESCRIPTION
        "This object is defined in TR-181 Device.WiFi.SSID{i}.Alias."
    REFERENCE
    		"TR-181 Device Data Model for TR-069."
    ::= {clabWIFISSIDEntry 4 }

clabWIFISSIDName    OBJECT-TYPE
    SYNTAX      SnmpAdminString (SIZE(0..64)) 
    MAX-ACCESS  read-only
    STATUS      current
    DESCRIPTION
        "This object is defined in TR-181 Device.WiFi.SSID{i}.Name."
    REFERENCE
    		"TR-181 Device Data Model for TR-069."    ::= {clabWIFISSIDEntry 5 }

clabWIFISSIDLastChange    OBJECT-TYPE
    SYNTAX      Unsigned32 
    UNITS       "seconds"
    MAX-ACCESS  read-only
    STATUS      current
    DESCRIPTION
        "This object is defined in TR-181 Device.WiFi.SSID{i}.LastChange."
    REFERENCE
    		"TR-181 Device Data Model for TR-069."
    ::= {clabWIFISSIDEntry 6 }

clabWIFISSIDLowerLayers    OBJECT-TYPE
    SYNTAX      SnmpAdminString (SIZE(0..1024))
    MAX-ACCESS  read-create
    STATUS      current
    DESCRIPTION
        "This object is defined in TR-181 Device.WiFi.SSID{i}.LowerLayers."
    REFERENCE
    		"TR-181 Device Data Model for TR-069."
    ::= {clabWIFISSIDEntry 7 }

clabWIFISSIDBSSID    OBJECT-TYPE
    SYNTAX      MacAddress 
    MAX-ACCESS  read-only
    STATUS      current
    DESCRIPTION
        "This object is defined in TR-181 Device.WiFi.SSID{i}.BSSID."
    REFERENCE
    		"TR-181 Device Data Model for TR-069."
    ::= {clabWIFISSIDEntry 8 }

clabWIFISSIDMACAddress    OBJECT-TYPE
    SYNTAX      MacAddress 
    MAX-ACCESS  read-only
    STATUS      current
    DESCRIPTION
        "This object is defined in TR-181 Device.WiFi.SSID{i}.MACAddress."
    REFERENCE
    		"TR-181 Device Data Model for TR-069."
    ::= {clabWIFISSIDEntry 9 }

clabWIFISSIDSSID    OBJECT-TYPE
    SYNTAX      SnmpAdminString (SIZE(0..32))
    MAX-ACCESS  read-create
    STATUS      current
    DESCRIPTION
        "This object is defined in TR-181 Device.WiFi.SSID{i}.SSID."
    REFERENCE
    		"TR-181 Device Data Model for TR-069."
    ::= {clabWIFISSIDEntry 10 }

clabWIFISSIDRowStatus    OBJECT-TYPE
    SYNTAX      RowStatus 
    MAX-ACCESS  read-create
    STATUS      current
    DESCRIPTION
        "The status of this instance"
    ::= {clabWIFISSIDEntry 11 }
    
clabWIFISSIDStatsTable OBJECT-TYPE
    SYNTAX      SEQUENCE OF ClabWIFISSIDStatsEntry
    MAX-ACCESS  not-accessible
    STATUS      current
    DESCRIPTION
        "This object is defined in TR-181 Device.WiFi.SSID{i}.Stats."
    REFERENCE
    		"TR-181 Device Data Model for TR-069."
    ::= {clabWIFIObjects 5 }

clabWIFISSIDStatsEntry    OBJECT-TYPE
    SYNTAX      ClabWIFISSIDStatsEntry
    MAX-ACCESS  not-accessible
    STATUS      current
    DESCRIPTION
        "The Conceptual row of clabWIFISSIDStatsTable."
    REFERENCE
        "TR-181 Issue2"
    INDEX {
            clabWIFISSIDId
          }
    ::= {clabWIFISSIDStatsTable 1 }

ClabWIFISSIDStatsEntry ::= SEQUENCE {
    clabWIFISSIDStatsBytesSent
                 Counter64,
    clabWIFISSIDStatsBytesReceived
                 Counter64,
    clabWIFISSIDStatsPacketsSent
                 Counter64,
    clabWIFISSIDStatsPacketsReceived
                 Counter64,
    clabWIFISSIDStatsErrorsSent
                 Counter32,
    clabWIFISSIDStatsErrorsReceived
                 Counter32,
    clabWIFISSIDStatsUnicastPacketsSent
                 Counter64,
    clabWIFISSIDStatsUnicastPacketsReceived
                 Counter64,
    clabWIFISSIDStatsDiscardPacketsSent
                 Counter32,
    clabWIFISSIDStatsDiscardPacketsReceived
                 Counter32,
    clabWIFISSIDStatsMulticastPacketsSent
                 Counter64,
    clabWIFISSIDStatsMulticastPacketsReceived
                 Counter64,
    clabWIFISSIDStatsBroadcastPacketsSent
                 Counter64,
    clabWIFISSIDStatsBroadcastPacketsReceived
                 Counter64,
    clabWIFISSIDStatsUnknownProtoPacketsReceived
                 Counter32
      }

clabWIFISSIDStatsBytesSent    OBJECT-TYPE
    SYNTAX      Counter64 
    MAX-ACCESS  read-only
    STATUS      current
    DESCRIPTION
        "This object is defined in TR-181 Device.WiFi.SSID{i}.Stats.BytesSent."
    REFERENCE
    		"TR-181 Device Data Model for TR-069."
    ::= {clabWIFISSIDStatsEntry 1 }

clabWIFISSIDStatsBytesReceived    OBJECT-TYPE
    SYNTAX      Counter64 
    MAX-ACCESS  read-only
    STATUS      current
    DESCRIPTION
        "This object is defined in TR-181 Device.WiFi.SSID{i}.Stats.BytesReceived."
    REFERENCE
    		"TR-181 Device Data Model for TR-069."
    ::= {clabWIFISSIDStatsEntry 2 }

clabWIFISSIDStatsPacketsSent    OBJECT-TYPE
    SYNTAX      Counter64 
    MAX-ACCESS  read-only
    STATUS      current
    DESCRIPTION
        "This object is defined in TR-181 Device.WiFi.SSID{i}.Stats.PacketsSent."
    REFERENCE
    		"TR-181 Device Data Model for TR-069."
    ::= {clabWIFISSIDStatsEntry 3 }

clabWIFISSIDStatsPacketsReceived    OBJECT-TYPE
    SYNTAX      Counter64 
    MAX-ACCESS  read-only
    STATUS      current
    DESCRIPTION
        "This object is defined in TR-181 Device.WiFi.SSID{i}.Stats.PacketsReceived."
    REFERENCE
    		"TR-181 Device Data Model for TR-069."
    ::= {clabWIFISSIDStatsEntry 4 }

clabWIFISSIDStatsErrorsSent    OBJECT-TYPE
    SYNTAX      Counter32 
    MAX-ACCESS  read-only
    STATUS      current
    DESCRIPTION
        "This object is defined in TR-181 Device.WiFi.SSID{i}.Stats.ErrorsSent."
    REFERENCE
    		"TR-181 Device Data Model for TR-069."
    ::= {clabWIFISSIDStatsEntry 5 }

clabWIFISSIDStatsErrorsReceived    OBJECT-TYPE
    SYNTAX      Counter32 
    MAX-ACCESS  read-only
    STATUS      current
    DESCRIPTION
        "This object is defined in TR-181 Device.WiFi.SSID{i}.Stats.ErrorsReceived."
    REFERENCE
    		"TR-181 Device Data Model for TR-069."
    ::= {clabWIFISSIDStatsEntry 6 }

clabWIFISSIDStatsUnicastPacketsSent    OBJECT-TYPE
    SYNTAX      Counter64 
    MAX-ACCESS  read-only
    STATUS      current
    DESCRIPTION
        "This object is defined in TR-181 Device.WiFi.SSID{i}.Stats.UnicastPacketsSent."
    REFERENCE
    		"TR-181 Device Data Model for TR-069."
    ::= {clabWIFISSIDStatsEntry 7 }

clabWIFISSIDStatsUnicastPacketsReceived    OBJECT-TYPE
    SYNTAX      Counter64 
    MAX-ACCESS  read-only
    STATUS      current
    DESCRIPTION
        "This object is defined in TR-181 Device.WiFi.SSID{i}.Stats.UnicastPacketsReceived."
    REFERENCE
    		"TR-181 Device Data Model for TR-069."
    ::= {clabWIFISSIDStatsEntry 8 }

clabWIFISSIDStatsDiscardPacketsSent    OBJECT-TYPE
    SYNTAX      Counter32 
    MAX-ACCESS  read-only
    STATUS      current
    DESCRIPTION
        "This object is defined in TR-181 Device.WiFi.SSID{i}.Stats.DiscardPacketsSent."
    REFERENCE
    		"TR-181 Device Data Model for TR-069."
    ::= {clabWIFISSIDStatsEntry 9 }

clabWIFISSIDStatsDiscardPacketsReceived    OBJECT-TYPE
    SYNTAX      Counter32 
    MAX-ACCESS  read-only
    STATUS      current
    DESCRIPTION
        "This object is defined in TR-181 Device.WiFi.SSID{i}.Stats.DiscardPacketsReceived."
    REFERENCE
    		"TR-181 Device Data Model for TR-069."
    ::= {clabWIFISSIDStatsEntry 10 }

clabWIFISSIDStatsMulticastPacketsSent    OBJECT-TYPE
    SYNTAX      Counter64 
    MAX-ACCESS  read-only
    STATUS      current
    DESCRIPTION
        "This object is defined in TR-181 Device.WiFi.SSID{i}.Stats.MulticastPacketsSent."
    REFERENCE
    		"TR-181 Device Data Model for TR-069."
    ::= {clabWIFISSIDStatsEntry 11 }

clabWIFISSIDStatsMulticastPacketsReceived    OBJECT-TYPE
    SYNTAX      Counter64 
    MAX-ACCESS  read-only
    STATUS      current
    DESCRIPTION
        "This object is defined in TR-181 Device.WiFi.SSID{i}.Stats.MulticastPacketsReceived."
    REFERENCE
    		"TR-181 Device Data Model for TR-069."
    ::= {clabWIFISSIDStatsEntry 12 }

clabWIFISSIDStatsBroadcastPacketsSent    OBJECT-TYPE
    SYNTAX      Counter64 
    MAX-ACCESS  read-only
    STATUS      current
    DESCRIPTION
        "This object is defined in TR-181 Device.WiFi.SSID{i}.Stats.BroadcastPacketsSent."
    REFERENCE
    		"TR-181 Device Data Model for TR-069."
    ::= {clabWIFISSIDStatsEntry 13 }

clabWIFISSIDStatsBroadcastPacketsReceived    OBJECT-TYPE
    SYNTAX      Counter64 
    MAX-ACCESS  read-only
    STATUS      current
    DESCRIPTION
        "This object is defined in TR-181 Device.WiFi.SSID{i}.Stats.BroadcastPacketsReceived."
    REFERENCE
    		"TR-181 Device Data Model for TR-069."
    ::= {clabWIFISSIDStatsEntry 14 }

clabWIFISSIDStatsUnknownProtoPacketsReceived    OBJECT-TYPE
    SYNTAX      Counter32 
    MAX-ACCESS  read-only
    STATUS      current
    DESCRIPTION
        "This object is defined in TR-181 Device.WiFi.SSID{i}.Stats.UnknownProtoPacketsReceived."
    REFERENCE
    		"TR-181 Device Data Model for TR-069."
    ::= {clabWIFISSIDStatsEntry 15 }

clabWIFIAccessPointTable OBJECT-TYPE
    SYNTAX      SEQUENCE OF ClabWIFIAccessPointEntry
    MAX-ACCESS  not-accessible
    STATUS      current
    DESCRIPTION
        "This object is defined in TR-181 Device.WiFi.AccessPoint{i}."
    REFERENCE
    		"TR-181 Device Data Model for TR-069."
    ::= {clabWIFIObjects 6 }

clabWIFIAccessPointEntry    OBJECT-TYPE
    SYNTAX      ClabWIFIAccessPointEntry
    MAX-ACCESS  not-accessible
    STATUS      current
    DESCRIPTION
        "The Conceptual row of clabWIFIAccessPointTable."
    INDEX {
            clabWIFIAccessPointId
          }
    ::= {clabWIFIAccessPointTable 1 }

ClabWIFIAccessPointEntry ::= SEQUENCE {
    clabWIFIAccessPointId
                 Unsigned32,
    clabWIFIAccessPointEnable
                 TruthValue,
    clabWIFIAccessPointStatus
                 INTEGER,
    clabWIFIAccessPointAlias
                 SnmpAdminString,
    clabWIFIAccessPointSSIDReference
                 SnmpAdminString,
    clabWIFIAccessPointSSIDAdvertisementEnabled
                 TruthValue,
    clabWIFIAccessPointRetryLimit
                 Unsigned32,
    clabWIFIAccessPointWMMCapability
                 TruthValue,
    clabWIFIAccessPointUAPSDCapability
                 TruthValue,
    clabWIFIAccessPointWMMEnable
                 TruthValue,
    clabWIFIAccessPointUAPSDEnable
                 TruthValue,
    clabWIFIAccessPointAssociatedDeviceNumberOfEntries
                 Unsigned32,
    clabWIFIAccessPointAssociatedDeviceRowStatus 
                 RowStatus
      }

clabWIFIAccessPointId    OBJECT-TYPE
    SYNTAX      Unsigned32 
    MAX-ACCESS  not-accessible
    STATUS      current
    DESCRIPTION
        "The key for a unique instance of this object."
    ::= {clabWIFIAccessPointEntry 1 }

clabWIFIAccessPointEnable    OBJECT-TYPE
    SYNTAX      TruthValue 
    MAX-ACCESS  read-create
    STATUS      current
    DESCRIPTION
        "This object is defined in TR-181 Device.WiFi.AccessPoint{i}.Enable."
    REFERENCE
    		"TR-181 Device Data Model for TR-069."
    ::= {clabWIFIAccessPointEntry 2 }

clabWIFIAccessPointStatus    OBJECT-TYPE
    SYNTAX      INTEGER  {
                           disabled(1),
                           enabled(2),
                           errorMisconfigured(3),
                           error(4)
                         }
    MAX-ACCESS  read-only
    STATUS      current
    DESCRIPTION
        "This object is defined in TR-181 Device.WiFi.AccessPoint{i}.Status."
    REFERENCE
    		"TR-181 Device Data Model for TR-069."
    ::= {clabWIFIAccessPointEntry 3 }

clabWIFIAccessPointAlias    OBJECT-TYPE
    SYNTAX      SnmpAdminString (SIZE(0..64))
    MAX-ACCESS  read-create
    STATUS      current
    DESCRIPTION
        "This object is defined in TR-181 Device.WiFi.AccessPoint{i}.Alias."
    REFERENCE
    		"TR-181 Device Data Model for TR-069."
    ::= {clabWIFIAccessPointEntry 4 }

clabWIFIAccessPointSSIDReference    OBJECT-TYPE
    SYNTAX      SnmpAdminString 
    MAX-ACCESS  read-create
    STATUS      current
    DESCRIPTION
        "This object is defined in TR-181 Device.WiFi.AccessPoint{i}.Reference."
    REFERENCE
    		"TR-181 Device Data Model for TR-069."
    ::= {clabWIFIAccessPointEntry 5 }

clabWIFIAccessPointSSIDAdvertisementEnabled    OBJECT-TYPE
    SYNTAX      TruthValue 
    MAX-ACCESS  read-create
    STATUS      current
    DESCRIPTION
        "This object is defined in TR-181 Device.WiFi.AccessPoint{i}.AdvertisementEnabled."
    REFERENCE
    		"TR-181 Device Data Model for TR-069."
    ::= {clabWIFIAccessPointEntry 6 }

clabWIFIAccessPointRetryLimit    OBJECT-TYPE
    SYNTAX      Unsigned32 (0..7)
    MAX-ACCESS  read-create
    STATUS      current
    DESCRIPTION
        "This object is defined in TR-181 Device.WiFi.AccessPoint{i}.RetryLimit."
    REFERENCE
    		"TR-181 Device Data Model for TR-069."
    ::= {clabWIFIAccessPointEntry 7 }

clabWIFIAccessPointWMMCapability    OBJECT-TYPE
    SYNTAX      TruthValue 
    MAX-ACCESS  read-only
    STATUS      current
    DESCRIPTION
        "This object is defined in TR-181 Device.WiFi.AccessPoint{i}.WMMCapability."
    REFERENCE
    		"TR-181 Device Data Model for TR-069."
    ::= {clabWIFIAccessPointEntry 8 }

clabWIFIAccessPointUAPSDCapability    OBJECT-TYPE
    SYNTAX      TruthValue 
    MAX-ACCESS  read-only
    STATUS      current
    DESCRIPTION
        "This object is defined in TR-181 Device.WiFi.AccessPoint{i}.UAPSDCapability."
    REFERENCE
    		"TR-181 Device Data Model for TR-069."
    ::= {clabWIFIAccessPointEntry 9 }

clabWIFIAccessPointWMMEnable    OBJECT-TYPE
    SYNTAX      TruthValue 
    MAX-ACCESS  read-create
    STATUS      current
    DESCRIPTION
        "This object is defined in TR-181 Device.WiFi.AccessPoint{i}.WMMEnable."
    REFERENCE
    		"TR-181 Device Data Model for TR-069."
    ::= {clabWIFIAccessPointEntry 10 }

clabWIFIAccessPointUAPSDEnable    OBJECT-TYPE
    SYNTAX      TruthValue 
    MAX-ACCESS  read-create
    STATUS      current
    DESCRIPTION
        "This object is defined in TR-181 Device.WiFi.AccessPoint{i}.UAPSDEnable."
    REFERENCE
    		"TR-181 Device Data Model for TR-069."
    ::= {clabWIFIAccessPointEntry 11 }

clabWIFIAccessPointAssociatedDeviceNumberOfEntries    OBJECT-TYPE
    SYNTAX      Unsigned32 
    MAX-ACCESS  read-only
    STATUS      current
    DESCRIPTION
        "This object is defined in TR-181 Device.WiFi.AccessPoint{i}.AssociatedDeviceNumberOfEntries."
    REFERENCE
    		"TR-181 Device Data Model for TR-069."
    ::= {clabWIFIAccessPointEntry 12 }

clabWIFIAccessPointAssociatedDeviceRowStatus    OBJECT-TYPE
    SYNTAX      RowStatus 
    MAX-ACCESS  read-create
    STATUS      current
    DESCRIPTION
        "The status of this instance."
    ::= {clabWIFIAccessPointEntry 13 }

clabWIFIAccessPointSecurityTable OBJECT-TYPE
    SYNTAX      SEQUENCE OF ClabWIFIAccessPointSecurityEntry
    MAX-ACCESS  not-accessible
    STATUS      current
    DESCRIPTION
        "This object is defined in TR-181 Device.WiFi.AccessPoint{i}.Security.."
    REFERENCE
    		"TR-181 Device Data Model for TR-069."
    ::= {clabWIFIObjects 7 }

clabWIFIAccessPointSecurityEntry    OBJECT-TYPE
    SYNTAX      ClabWIFIAccessPointSecurityEntry
    MAX-ACCESS  not-accessible
    STATUS      current
    DESCRIPTION
        "The Conceptual row of clabWIFIAccessPointSecurityTable."
    REFERENCE
        "802.11-2007"
    INDEX {
            clabWIFIAccessPointId
          }
    ::= {clabWIFIAccessPointSecurityTable 1 }

ClabWIFIAccessPointSecurityEntry ::= SEQUENCE {
    clabWIFIAccessPointSecurityModesSupported
                 SnmpAdminString,
    clabWIFIAccessPointSecurityModeEnabled
                 INTEGER,
    clabWIFIAccessPointSecurityWEPKey
                 OCTET STRING,
    clabWIFIAccessPointSecurityPreSharedKey
                 OCTET STRING,
    clabWIFIAccessPointSecurityKeyPassphrase
                 SnmpAdminString,
    clabWIFIAccessPointSecurityRekeyingInterval
                 Unsigned32,
    clabWIFIAccessPointSecurityRadiusServerIPAddrType
                 InetAddressType,
    clabWIFIAccessPointSecurityRadiusServerIPAddr
                 InetAddress,
    clabWIFIAccessPointSecurityRadiusServerPort
                 InetPortNumber,
    clabWIFIAccessPointSecurityRadiusSecret
                 SnmpAdminString,
    clabWIFIAccessPointSecurityRowstatus
                 RowStatus
      }

clabWIFIAccessPointSecurityModesSupported    OBJECT-TYPE
    SYNTAX      SnmpAdminString
    MAX-ACCESS  read-only
    STATUS      current
    DESCRIPTION
        "This object is defined in TR-181 Device.WiFi.AccessPoint{i}.Security.ModesSupported."
    REFERENCE
    		"TR-181 Device Data Model for TR-069."
    ::= {clabWIFIAccessPointSecurityEntry 1 }

clabWIFIAccessPointSecurityModeEnabled    OBJECT-TYPE
    SYNTAX      INTEGER  {
                            none(1),
                            wep64(2),
                            wep128(3),
                            wpaPersonal(4),
                            wpa2Personal(5),
                            wpawpa2Personal(6),
                            wpaEnterprise(7),
                            wpa2Enterprise(8),
                            wpawpa2Enterprise(9)
                         }
    MAX-ACCESS  read-create
    STATUS      current
    DESCRIPTION
        "This object is defined in TR-181 Device.WiFi.AccessPoint{i}.Security.ModeEnabled."
    REFERENCE
    		"TR-181 Device Data Model for TR-069."
    ::= {clabWIFIAccessPointSecurityEntry 2 }

clabWIFIAccessPointSecurityWEPKey    OBJECT-TYPE
    SYNTAX      OCTET STRING (SIZE (0 | 5 | 13)) 
    MAX-ACCESS  read-create
    STATUS      current
    DESCRIPTION
        "This object is defined in TR-181 Device.WiFi.AccessPoint{i}.Security.WEPKey."
    REFERENCE
    		"TR-181 Device Data Model for TR-069."
    ::= {clabWIFIAccessPointSecurityEntry 3 }

clabWIFIAccessPointSecurityPreSharedKey    OBJECT-TYPE
    SYNTAX      OCTET STRING (SIZE(0 | 32)) 
    MAX-ACCESS  read-create
    STATUS      current
    DESCRIPTION
        "This object is defined in TR-181 Device.WiFi.AccessPoint{i}.Security.PreSharedKey."
    REFERENCE
    		"TR-181 Device Data Model for TR-069."
    ::= {clabWIFIAccessPointSecurityEntry 4 }

clabWIFIAccessPointSecurityKeyPassphrase    OBJECT-TYPE
    SYNTAX      SnmpAdminString (SIZE(0..63))  
    MAX-ACCESS  read-create
    STATUS      current
    DESCRIPTION
        "This object is defined in TR-181 Device.WiFi.AccessPoint{i}.Security.KeyPassphrase."
    REFERENCE
    		"TR-181 Device Data Model for TR-069."
    ::= {clabWIFIAccessPointSecurityEntry 5 }

clabWIFIAccessPointSecurityRekeyingInterval    OBJECT-TYPE
    SYNTAX      Unsigned32 
    UNITS       "seconds"
    MAX-ACCESS  read-create
    STATUS      current
    DESCRIPTION
        "This object is defined in TR-181 Device.WiFi.AccessPoint{i}.Security.RekeyingInterval."
    REFERENCE
    		"TR-181 Device Data Model for TR-069."
    ::= {clabWIFIAccessPointSecurityEntry 6 }

clabWIFIAccessPointSecurityRadiusServerIPAddrType    OBJECT-TYPE
    SYNTAX      InetAddressType 
    MAX-ACCESS  read-create
    STATUS      current
    DESCRIPTION
        "This object is defined in TR-181 Device.WiFi.AccessPoint{i}.Security.RadiusServerIPAddrType."
    REFERENCE
    		"TR-181 Device Data Model for TR-069."
    ::= {clabWIFIAccessPointSecurityEntry 7 }

clabWIFIAccessPointSecurityRadiusServerIPAddr    OBJECT-TYPE
    SYNTAX      InetAddress 
    MAX-ACCESS  read-create
    STATUS      current
    DESCRIPTION
        "This object is defined in TR-181 Device.WiFi.AccessPoint{i}.Security.RadiusServerIPAddr."
    REFERENCE
    		"TR-181 Device Data Model for TR-069."
    ::= {clabWIFIAccessPointSecurityEntry 8 }

clabWIFIAccessPointSecurityRadiusServerPort    OBJECT-TYPE
    SYNTAX      InetPortNumber 
    MAX-ACCESS  read-create
    STATUS      current
    DESCRIPTION
        "This object is defined in TR-181 Device.WiFi.AccessPoint{i}.Security.RadiusServerPort."
    REFERENCE
    		"TR-181 Device Data Model for TR-069."
    ::= {clabWIFIAccessPointSecurityEntry 9 }

clabWIFIAccessPointSecurityRadiusSecret    OBJECT-TYPE
    SYNTAX      SnmpAdminString 
    MAX-ACCESS  read-create
    STATUS      current
    DESCRIPTION
        "This object is defined in TR-181 Device.WiFi.AccessPoint{i}.Security.RadiusSecret."
    REFERENCE
    		"TR-181 Device Data Model for TR-069."
    ::= {clabWIFIAccessPointSecurityEntry 10 }

clabWIFIAccessPointSecurityRowstatus    OBJECT-TYPE
    SYNTAX      RowStatus 
    MAX-ACCESS  read-create
    STATUS      current
    DESCRIPTION
        "The status of this instance."
    ::= {clabWIFIAccessPointSecurityEntry 11 }

clabWIFIAccessPointWPSTable OBJECT-TYPE
    SYNTAX      SEQUENCE OF ClabWIFIAccessPointWPSEntry
    MAX-ACCESS  not-accessible
    STATUS      current
    DESCRIPTION
        "This object is defined in TR-181 Device.WiFi.AccessPoint{i}.WPS."
    REFERENCE
    		"TR-181 Device Data Model for TR-069."
    ::= {clabWIFIObjects 8 }

clabWIFIAccessPointWPSEntry    OBJECT-TYPE
    SYNTAX      ClabWIFIAccessPointWPSEntry
    MAX-ACCESS  not-accessible
    STATUS      current
    DESCRIPTION
        "The Conceptual row of clabWIFIAccessPointWPSTable."
    REFERENCE
        "WPSv1.0"
    INDEX {
            clabWIFIAccessPointId
          }
    ::= {clabWIFIAccessPointWPSTable 1 }

ClabWIFIAccessPointWPSEntry ::= SEQUENCE {
    clabWIFIAccessPointWPSEnable
                 TruthValue,
    clabWIFIAccessPointWPSConfigMethodsSupported
                 SnmpAdminString,
    clabWIFIAccessPointWPSConfigMethodsEnabled
                 INTEGER,
    clabWIFIAccessPointWPSRowStatus
                 RowStatus
      }

clabWIFIAccessPointWPSEnable    OBJECT-TYPE
    SYNTAX      TruthValue 
    MAX-ACCESS  read-create
    STATUS      current
    DESCRIPTION
        "This object is defined in TR-181 Device.WiFi.AccessPoint{i}.WPS.Enable."
    REFERENCE
    		"TR-181 Device Data Model for TR-069."
    ::= {clabWIFIAccessPointWPSEntry 1 }

clabWIFIAccessPointWPSConfigMethodsSupported    OBJECT-TYPE
    SYNTAX      SnmpAdminString
    MAX-ACCESS  read-only
    STATUS      current
    DESCRIPTION
        "This object is defined in TR-181 Device.WiFi.AccessPoint{i}.WPS.ConfigMethodsSupported."
    REFERENCE
    		"TR-181 Device Data Model for TR-069."
    ::= {clabWIFIAccessPointWPSEntry 2 }

clabWIFIAccessPointWPSConfigMethodsEnabled    OBJECT-TYPE
    SYNTAX      INTEGER  {
                            usbFlashDrive(1),
                            ethernet(2),
                            externalNFCToken(3),
                            integratedNFCToken(4),
                            nfcInterface(5),
                            pin(7),
                            pushButton(8)
                         }
    MAX-ACCESS  read-create
    STATUS      current
    DESCRIPTION
        "This object is defined in TR-181 Device.WiFi.AccessPoint{i}.WPS.ConfigMethodsEnabled."
    REFERENCE
    		"TR-181 Device Data Model for TR-069."
    ::= {clabWIFIAccessPointWPSEntry 3 }

clabWIFIAccessPointWPSRowStatus    OBJECT-TYPE
    SYNTAX      RowStatus
    MAX-ACCESS  read-create
    STATUS      current
    DESCRIPTION
        "The status of this instance."
    ::= {clabWIFIAccessPointWPSEntry 4 } 


clabWIFIAssociatedDeviceTable OBJECT-TYPE
    SYNTAX      SEQUENCE OF ClabWIFIAssociatedDeviceEntry
    MAX-ACCESS  not-accessible
    STATUS      current
    DESCRIPTION
        "This object is defined in TR-181 Device.WiFi.AssociatedDevice{i}."
    REFERENCE
    		"TR-181 Device Data Model for TR-069."
    ::= {clabWIFIObjects 9 }

clabWIFIAssociatedDeviceEntry    OBJECT-TYPE
    SYNTAX      ClabWIFIAssociatedDeviceEntry
    MAX-ACCESS  not-accessible
    STATUS      current
    DESCRIPTION
        "The Conceptual row of clabWIFIAssociatedDeviceTable."
    INDEX {
            clabWIFIAccessPointId, clabWIFIAssociatedDeviceId
          }
    ::= {clabWIFIAssociatedDeviceTable 1 }

ClabWIFIAssociatedDeviceEntry ::= SEQUENCE {
    clabWIFIAssociatedDeviceId
                 Unsigned32,
    clabWIFIAssociatedDeviceMACAddress
                 MacAddress,
    clabWIFIAssociatedDeviceAuthenticationState
                 TruthValue,
    clabWIFIAssociatedDeviceLastDataDownlinkRate
                 Unsigned32,
    clabWIFIAssociatedDeviceLastDataUplinkRate
                 Unsigned32,
    clabWIFIAssociatedDeviceSignalStrength
                 Integer32,
    clabWIFIAssociatedDeviceRetransmissions
                 Unsigned32,
    clabWIFIAssociatedDeviceActive
                 TruthValue
      }

clabWIFIAssociatedDeviceId    OBJECT-TYPE
    SYNTAX      Unsigned32 
    MAX-ACCESS  not-accessible
    STATUS      current
    DESCRIPTION
        "The key for a unique instance of this object. There is one 
        instance for each unique Associated device MAC Address."
    ::= {clabWIFIAssociatedDeviceEntry 1 }

clabWIFIAssociatedDeviceMACAddress    OBJECT-TYPE
    SYNTAX      MacAddress 
    MAX-ACCESS  read-only
    STATUS      current
    DESCRIPTION
        "This object is defined in TR-181 Device.WiFi.AssociatedDevice{i}.MACAddress."
    REFERENCE
    		"TR-181 Device Data Model for TR-069."
    ::= {clabWIFIAssociatedDeviceEntry 2 }

clabWIFIAssociatedDeviceAuthenticationState    OBJECT-TYPE
    SYNTAX      TruthValue 
    MAX-ACCESS  read-only
    STATUS      current
    DESCRIPTION
        "This object is defined in TR-181 Device.WiFi.AssociatedDevice{i}.AuthenticationState."
    REFERENCE
    		"TR-181 Device Data Model for TR-069."
    ::= {clabWIFIAssociatedDeviceEntry 3 }

clabWIFIAssociatedDeviceLastDataDownlinkRate    OBJECT-TYPE
    SYNTAX      Unsigned32 
    UNITS       "kbps"
    MAX-ACCESS  read-only
    STATUS      current
    DESCRIPTION
        "This object is defined in TR-181 Device.WiFi.AssociatedDevice{i}.LastDataDownlinkRate."
    REFERENCE
    		"TR-181 Device Data Model for TR-069."
    ::= {clabWIFIAssociatedDeviceEntry 4 }

clabWIFIAssociatedDeviceLastDataUplinkRate    OBJECT-TYPE
    SYNTAX      Unsigned32 
    UNITS       "kbps"
    MAX-ACCESS  read-only
    STATUS      current
    DESCRIPTION
        "This object is defined in TR-181 Device.WiFi.AssociatedDevice{i}.DeviceLastDataUplinkRate."
    REFERENCE
    		"TR-181 Device Data Model for TR-069."
    ::= {clabWIFIAssociatedDeviceEntry 5 }

clabWIFIAssociatedDeviceSignalStrength    OBJECT-TYPE
    SYNTAX      Integer32 
    UNITS       "dBm"
    MAX-ACCESS  read-only
    STATUS      current
    DESCRIPTION
        "This object is defined in TR-181 Device.WiFi.AssociatedDevice{i}.SignalStrength."
    REFERENCE
    		"TR-181 Device Data Model for TR-069."
    ::= {clabWIFIAssociatedDeviceEntry 6 }

clabWIFIAssociatedDeviceRetransmissions    OBJECT-TYPE
    SYNTAX      Unsigned32 
    UNITS       "packets"
    MAX-ACCESS  read-only
    STATUS      current
    DESCRIPTION
        "This object is defined in TR-181 Device.WiFi.AssociatedDevice{i}.Retransmissions."
    REFERENCE
    		"TR-181 Device Data Model for TR-069."
    ::= {clabWIFIAssociatedDeviceEntry 7 }

clabWIFIAssociatedDeviceActive    OBJECT-TYPE
    SYNTAX      TruthValue 
    MAX-ACCESS  read-only
    STATUS      current
    DESCRIPTION
        "This object is defined in TR-181 Device.WiFi.AssociatedDevice{i}.Active."
    REFERENCE
    		"TR-181 Device Data Model for TR-069."
    ::= {clabWIFIAssociatedDeviceEntry 8 }

clabWIFIDataRateStatsTable OBJECT-TYPE
    SYNTAX      SEQUENCE OF ClabWIFIDataRateStatsEntry
    MAX-ACCESS  not-accessible
    STATUS      current
    DESCRIPTION
        "This object contains statistics for each speed rate of 
        an 802.11 LAN interface."
    ::= {clabWIFIObjects 10 }

clabWIFIDataRateStatsEntry    OBJECT-TYPE
    SYNTAX      ClabWIFIDataRateStatsEntry
    MAX-ACCESS  not-accessible
    STATUS      current
    DESCRIPTION
        "The Conceptual row of clabWIFIDataRateStatsTable."
    INDEX {
            clabWIFIRadioId, clabWIFIDataRateStatsRate
          }
    ::= {clabWIFIDataRateStatsTable 1 }

ClabWIFIDataRateStatsEntry ::= SEQUENCE {
    clabWIFIDataRateStatsRate
                 Unsigned32,
    clabWIFIDataRateStatsFramesSent
                 Counter64,
    clabWIFIDataRateStatsFramesRetransmissionsSent
                 Counter64,
    clabWIFIDataRateStatsFramesReceived
                 Counter64,
    clabWIFIDataRateStatsFramesDuplicatedReceived
                 Counter64
      }

clabWIFIDataRateStatsRate    OBJECT-TYPE
    SYNTAX      Unsigned32 
    UNITS       "Mbps"
    MAX-ACCESS  not-accessible
    STATUS      current
    DESCRIPTION
        "This key represents the data speed for the statistics 
        collected. the value is reported in integer units of Mbps."
    ::= {clabWIFIDataRateStatsEntry 1 }

clabWIFIDataRateStatsFramesSent    OBJECT-TYPE
    SYNTAX      Counter64 
    UNITS       "frames"
    MAX-ACCESS  read-only
    STATUS      current
    DESCRIPTION
        "The FramesSent Parameter indicates the total number of frames 
        transmitted out of the interface (not marked as duplicated).
The value of this counter MAY be reset to zero when the CPE is rebooted."
    ::= {clabWIFIDataRateStatsEntry 2 }

clabWIFIDataRateStatsFramesRetransmissionsSent    OBJECT-TYPE
    SYNTAX      Counter64 
    UNITS       "frames"
    MAX-ACCESS  read-only
    STATUS      current
    DESCRIPTION
        "The FramesRetransmissionsSent parameter indicates the total 
        number of frames retransmitted out of the interface (marked 
        as duplicated).
        The value of this counter MAY be reset to zero when the CPE 
        is rebooted."
    ::= {clabWIFIDataRateStatsEntry 3 }

clabWIFIDataRateStatsFramesReceived    OBJECT-TYPE
    SYNTAX      Counter64 
    UNITS       "frames"
    MAX-ACCESS  read-only
    STATUS      current
    DESCRIPTION
        "The FramesReceived parameter indicates the total number of 
        frames received on this interface (not marked as duplicated).
        The value of this counter MAY be reset to zero when the CPE is 
        rebooted."
    ::= {clabWIFIDataRateStatsEntry 4 }

clabWIFIDataRateStatsFramesDuplicatedReceived    OBJECT-TYPE
    SYNTAX      Counter64 
    UNITS       "frames"
    MAX-ACCESS  read-only
    STATUS      current
    DESCRIPTION
        "The FramesDuplicatedReceived indicates the total number of 
        duplicated frames received on this interface.
        The value of this counter MAY be reset to zero when the CPE 
        is rebooted."
    ::= {clabWIFIDataRateStatsEntry 5 }

clabWIFIPeriodicStatsTable OBJECT-TYPE
    SYNTAX      SEQUENCE OF ClabWIFIPeriodicStatsEntry
    MAX-ACCESS  not-accessible
    STATUS      current
    DESCRIPTION
        "This object contains periodic statistics for an 802.11 SSID 
        on a CPE device. Note that these statistics refer to the link 
        layer, not to the physical layer. This object does not include 
        the total byte and packet statistics, which are, for 
        historical reasons, in the parent object."
    ::= {clabWIFIObjects 11 }

clabWIFIPeriodicStatsEntry    OBJECT-TYPE
    SYNTAX      ClabWIFIPeriodicStatsEntry
    MAX-ACCESS  not-accessible
    STATUS      current
    DESCRIPTION
        "The Conceptual row of clabWIFIPeriodicStatsTable."
    INDEX {
            clabWIFISSIDId, 
            clabWIFIPeriodicStatsInterval, 
            clabWIFIPeriodicStatsId
          }
    ::= {clabWIFIPeriodicStatsTable 1 }

ClabWIFIPeriodicStatsEntry ::= SEQUENCE {
    clabWIFIPeriodicStatsInterval
                 Unsigned32,
    clabWIFIPeriodicStatsId
                 Unsigned32,
    clabWIFIPeriodicStatsDeviceMACAddress
                 MacAddress,
    clabWIFIPeriodicStatsFramesSent
                 Counter64,
    clabWIFIPeriodicStatsDataFramesSentAck
                 Counter64,
    clabWIFIPeriodicStatsDataFramesSentNoAck
                 Counter64,
    clabWIFIPeriodicStatsDataFramesLost
                 Counter64,
    clabWIFIPeriodicStatsFramesReceived
                 Counter64,
    clabWIFIPeriodicStatsDataFramesReceived
                 Counter64,
    clabWIFIPeriodicStatsDataFramesDuplicateReceived
                 Counter64,
    clabWIFIPeriodicStatsProbesReceived
                 Counter32,
    clabWIFIPeriodicStatsProbesRejected
                 Counter32,
    clabWIFIPeriodicStatsRSSI
                 Integer32,
    clabWIFIPeriodicStatsSNR
                 Integer32,
    clabWIFIPeriodicStatsDisassociations
                 Counter32,
    clabWIFIPeriodicStatsAuthenticationFailures
                 Counter32,
    clabWIFIPeriodicStatsLastTimeAssociation
                 DateAndTime,
    clabWIFIPeriodicStatsLastTimeDisassociation
                 DateAndTime
      }

clabWIFIPeriodicStatsInterval    OBJECT-TYPE
    SYNTAX      Unsigned32 (0 | 24 | 48 | 96 )
    MAX-ACCESS  not-accessible
    STATUS      current
    DESCRIPTION
        "This key indicates the Interval where the measurements were 
        accumulated
        The interval of measurements is synchronized with the wall clock.
        The total number of intervals is based on a 24 hour period. 
        At an interval of 15 minutes 96 intervals (1..96)  are defined, 
        at 30 minutes, 48 intervals (1..48) and 24 intervals (1..24) 
        for 1 hour measurement interval.
        Devices with  no capabilities to report measurements per interval 
        will report the value 0 for the interval attribute of the unique 
        statistics  instance."
    ::= {clabWIFIPeriodicStatsEntry 1 }

clabWIFIPeriodicStatsId    OBJECT-TYPE
    SYNTAX      Unsigned32 
    MAX-ACCESS  not-accessible
    STATUS      current
    DESCRIPTION
        "The Id key represents a unique identifier for a client 
        Mac address in a given statistics measurement interval."
    ::= {clabWIFIPeriodicStatsEntry 2 }

clabWIFIPeriodicStatsDeviceMACAddress    OBJECT-TYPE
    SYNTAX      MacAddress 
    MAX-ACCESS  read-only
    STATUS      current
    DESCRIPTION
        "The DeviceMACAddress represents the MAC address of an 
        associated client device."
    ::= {clabWIFIPeriodicStatsEntry 3 }

clabWIFIPeriodicStatsFramesSent    OBJECT-TYPE
    SYNTAX      Counter64 
    UNITS       "frames"
    MAX-ACCESS  read-only
    STATUS      current
    DESCRIPTION
        "FrameSent is the total number of frames transmitted out of 
        the interface.
        For conventional 802.11 MAC (a,b,g) this counter corresponds 
        to the total of MSDUs (MAC Service Data Unit) being transmitted.
        For High Throughput transmissions this corresponds to the 
        A-MSDU (Aggregation MSDU)
        The value of this counter MAY be reset to zero when the 
        CPE is rebooted."
    ::= {clabWIFIPeriodicStatsEntry 4 }

clabWIFIPeriodicStatsDataFramesSentAck    OBJECT-TYPE
    SYNTAX      Counter64 
    UNITS       "frames"
    MAX-ACCESS  read-only
    STATUS      current
    DESCRIPTION
        "DataFramesSentAck is the total number of MSDU frames marked 
        as duplicates and non duplicates acknowledged.
        The value of this counter MAY be reset to zero when the CPE 
        is rebooted."
    ::= {clabWIFIPeriodicStatsEntry 5 }

clabWIFIPeriodicStatsDataFramesSentNoAck    OBJECT-TYPE
    SYNTAX      Counter64 
    UNITS       "frames"
    MAX-ACCESS  read-only
    STATUS      current
    DESCRIPTION
        "DataFramesSentNoAck is the total number of MSDU frames 
        retransmitted out of the interface (i.e., marked as duplicate 
        and non-duplicate) and not acknowledged but not including 
        those defined in dataFramesLost.
        The value of this counter MAY be reset to zero when the 
        CPE is rebooted."
    ::= {clabWIFIPeriodicStatsEntry 6 }

clabWIFIPeriodicStatsDataFramesLost    OBJECT-TYPE
    SYNTAX      Counter64 
    UNITS       "frames"
    MAX-ACCESS  read-only
    STATUS      current
    DESCRIPTION
        "DataFramesLost is the total number of MSDU frames retransmitted 
        out of the interface that where not acknowledged and discarded 
        for reaching max number of retransmissions.
        The value of this counter MAY be reset to zero when the CPE 
        is rebooted."
    ::= {clabWIFIPeriodicStatsEntry 7 }

clabWIFIPeriodicStatsFramesReceived    OBJECT-TYPE
    SYNTAX      Counter64 
    UNITS       "frames"
    MAX-ACCESS  read-only
    STATUS      current
    DESCRIPTION
        "FramesReceived is the total number of frames received by the 
        interface.
        For conventional 802.11 MAC (a,b,g) this counter corresponds to the 
        total of MSDUs (MAC Service Data Unit) being transmitted.
        For High Throughput transmissions (n) this corresponds to A-MSDUs 
        (Aggregation MSDU) and MSDUs.
        The value of this counter MAY be reset to zero when the CPE 
        is rebooted."
    ::= {clabWIFIPeriodicStatsEntry 8 }

clabWIFIPeriodicStatsDataFramesReceived    OBJECT-TYPE
    SYNTAX      Counter64 
    UNITS       "frames"
    MAX-ACCESS  read-only
    STATUS      current
    DESCRIPTION
        "DataFramesReceived is the total number of MSDU frames 
        received and  marked as non-duplicates.
        The value of this counter MAY be reset to zero when the CPE 
        is rebooted."
    ::= {clabWIFIPeriodicStatsEntry 9 }

clabWIFIPeriodicStatsDataFramesDuplicateReceived    OBJECT-TYPE
    SYNTAX      Counter64 
    UNITS       "frames"
    MAX-ACCESS  read-only
    STATUS      current
    DESCRIPTION
        "DataFramesDuplicateReceived is the total number of duplicated 
        frames received on this interface.
        The value of this counter MAY be reset to zero when the 
        CPE is rebooted."
    ::= {clabWIFIPeriodicStatsEntry 10 }

clabWIFIPeriodicStatsProbesReceived    OBJECT-TYPE
    SYNTAX      Counter32 
    UNITS       "probes"
    MAX-ACCESS  read-only
    STATUS      current
    DESCRIPTION
        "ProbesReceived is the total number of probes received."
    ::= {clabWIFIPeriodicStatsEntry 11 }

clabWIFIPeriodicStatsProbesRejected    OBJECT-TYPE
    SYNTAX      Counter32 
    UNITS       "probes"
    MAX-ACCESS  read-only
    STATUS      current
    DESCRIPTION
        "ProbesRejected is the total number of probes rejected."
    ::= {clabWIFIPeriodicStatsEntry 12 }

clabWIFIPeriodicStatsRSSI    OBJECT-TYPE
    SYNTAX      Integer32 
    UNITS       "dBm"
    MAX-ACCESS  read-only
    STATUS      current
    DESCRIPTION
        "The Received Signal Strength indicator is the energy observed 
        at the antenna receiver for a current transmission."
    ::= {clabWIFIPeriodicStatsEntry 13 }

clabWIFIPeriodicStatsSNR    OBJECT-TYPE
    SYNTAX      Integer32 
    UNITS       "dB"
    MAX-ACCESS  read-only
    STATUS      current
    DESCRIPTION
        "The signal to Noise Ratio (SNR) parameter represents the strength 
        of the signal compared to received noise."
    ::= {clabWIFIPeriodicStatsEntry 14 }

clabWIFIPeriodicStatsDisassociations    OBJECT-TYPE
    SYNTAX      Counter32 
    UNITS       "disassociations"
    MAX-ACCESS  read-only
    STATUS      current
    DESCRIPTION
        "Disassociations represents the total number of client 
        disassociations."
    ::= {clabWIFIPeriodicStatsEntry 15 }

clabWIFIPeriodicStatsAuthenticationFailures    OBJECT-TYPE
    SYNTAX      Counter32 
    UNITS       "authenticationfailures"
    MAX-ACCESS  read-only
    STATUS      current
    DESCRIPTION
        "AuthenticationFailures indicates the total number of 
        authentication failures."
    ::= {clabWIFIPeriodicStatsEntry 16 }

clabWIFIPeriodicStatsLastTimeAssociation    OBJECT-TYPE
    SYNTAX      DateAndTime 
    MAX-ACCESS  read-only
    STATUS      current
    DESCRIPTION
        "The LastTimeAssociation parameter represents the last 
        time the client was associated."
    ::= {clabWIFIPeriodicStatsEntry 17 }

clabWIFIPeriodicStatsLastTimeDisassociation    OBJECT-TYPE
    SYNTAX      DateAndTime 
    MAX-ACCESS  read-only
    STATUS      current
    DESCRIPTION
        "LastTimeDisassociation parameter represents the last time 
        the client disassociate from the interface. 
The all zeros value indicates the client is currently associated. "
    ::= {clabWIFIPeriodicStatsEntry 18 }

clabWIFISSIDPolicyTable OBJECT-TYPE
    SYNTAX      SEQUENCE OF ClabWIFISSIDPolicyEntry
    MAX-ACCESS  not-accessible
    STATUS      current
    DESCRIPTION
        "The SSIDPolicy object defines the configuration of policies, 
        behaviors and event thresholds controlled per SSID."
    ::= {clabWIFIObjects 12 }

clabWIFISSIDPolicyEntry    OBJECT-TYPE
    SYNTAX      ClabWIFISSIDPolicyEntry
    MAX-ACCESS  not-accessible
    STATUS      current
    DESCRIPTION
        "The Conceptual row of clabWIFISSIDPolicyTable."
    INDEX {
            clabWIFISSIDId
          }
    ::= {clabWIFISSIDPolicyTable 1 }

ClabWIFISSIDPolicyEntry ::= SEQUENCE {
    clabWIFISSIDPolicyBlockAfterAttempts
                 Unsigned32,
    clabWIFISSIDPolicyAllocatedBandwidth
                 Unsigned32,
    clabWIFISSIDPolicyAuthenticationFailures
                 Unsigned32,
    clabWIFISSIDPolicyNonAuthenticatedTraffic
                 Unsigned32,
    clabWIFISSIDPolicyAssociationFailures
                 Unsigned32,
    clabWIFISSIDPolicyStatsInterval
                 Unsigned32,
    clabWIFISSIDPolicySNRThreshold
                 Integer32,
    clabWIFISSIDPolicyANPIThreshold
                 Integer32,
    clabWIFISSIDPolicyLowReceivedPowerThreshold
                 Integer32,
    clabWIFISSIDPolicyLowPowerDeniedAccessThreshold
                 Integer32,
    clabWIFISSIDPolicyLowPowerDissasociationThreshold
                 Integer32,
    clabWIFISSIDPolicyRowStatus
                 RowStatus             
      }

clabWIFISSIDPolicyBlockAfterAttempts    OBJECT-TYPE
    SYNTAX      Unsigned32 
    MAX-ACCESS  read-create
    STATUS      current
    DESCRIPTION
        "The BlockAfterAttempts parameter indicates the maximum number 
        of attempts a client is allowed to attempt registration before 
        being denied access. Exceeding this value generates one event. 
        Events from same client should not reoccur more than once an 
        hour.
        The value zero indicates no connection attempts restrictions."
    DEFVAL      { 0 }
    ::= {clabWIFISSIDPolicyEntry 1 }

clabWIFISSIDPolicyAllocatedBandwidth    OBJECT-TYPE
    SYNTAX      Unsigned32 
    UNITS       "Mbps"
    MAX-ACCESS  read-create
    STATUS      current
    DESCRIPTION
        "The AllocatedBandwidth parameter indicates the maximum 
        bandwidth reserved for a particular interface. 
The value zero indicates no limit."
    DEFVAL      { 0 }
    ::= {clabWIFISSIDPolicyEntry 2 }

clabWIFISSIDPolicyAuthenticationFailures    OBJECT-TYPE
    SYNTAX      Unsigned32 
    MAX-ACCESS  read-create
    STATUS      current
    DESCRIPTION
        "The AuthenticationFailures parameter indicates the number of 
        Authenticationfailures a station simultaneously produces to 
        generate the event.
        Events from same client should not reoccur more than once an 
        hour.
        The value 0 indicates no threshold and events of this type are 
        not generated."
    DEFVAL      { 0 }
    ::= {clabWIFISSIDPolicyEntry 3 }

clabWIFISSIDPolicyNonAuthenticatedTraffic    OBJECT-TYPE
    SYNTAX      Unsigned32
    MAX-ACCESS  read-create
    STATUS      current
    DESCRIPTION
        "The NonAuthenticatedTraffic parameter represents the number 
        of non-authenticated messages received from a station to generate 
        an event. Events from same client should not reoccur more 
        than once an hour.
        The value 0 indicates no threshold and events of this type are 
        not generated."
    DEFVAL      { 0 }
    ::= {clabWIFISSIDPolicyEntry 4 }

clabWIFISSIDPolicyAssociationFailures    OBJECT-TYPE
    SYNTAX      Unsigned32 
    MAX-ACCESS  read-create
    STATUS      current
    DESCRIPTION
        "The AssociationFailures indicates the number of simultaneous 
        association failures from a station to generate an event. 
        Events from same client should not reoccur more than once an 
        hour.
        The value 0 indicates no threshold and events of this type are 
        not generated."
    DEFVAL      { 0 }
    ::= {clabWIFISSIDPolicyEntry 5 }

clabWIFISSIDPolicyStatsInterval    OBJECT-TYPE
    SYNTAX      Unsigned32 
    UNITS       "minutes"
    MAX-ACCESS  read-create
    STATUS      current
    DESCRIPTION
        "The StatsInterval parameter indicates the interval value to 
        collect per-interval statistics.

        The value 0 indicates no interval and values reported are 
        snapshots at the time of the request. "
    DEFVAL      { 0 }
    ::= {clabWIFISSIDPolicyEntry 6 }

clabWIFISSIDPolicySNRThreshold    OBJECT-TYPE
    SYNTAX      Integer32 
    UNITS       "dB"
    MAX-ACCESS  read-create
    STATUS      current
    DESCRIPTION
        "The SNR parameter indicates the threshold to report SNR. 
        The value -100 indicates no threshold, and events of this 
        type are not generated."
    DEFVAL      { -100 }
    ::= {clabWIFISSIDPolicyEntry 7 }

clabWIFISSIDPolicyANPIThreshold    OBJECT-TYPE
    SYNTAX      Integer32 
    UNITS       "dBm"
    MAX-ACCESS  read-create
    STATUS      current
    DESCRIPTION
        "The ANPI parameter indicates the threshold to report the 
        Average Noise plus Interference. The value -100 indicates no 
        threshold, and events of this type are not generated."
    DEFVAL      { -100 }
    ::= {clabWIFISSIDPolicyEntry 8 }

clabWIFISSIDPolicyLowReceivedPowerThreshold    OBJECT-TYPE
    SYNTAX      Integer32 
    UNITS       "dBm"
    MAX-ACCESS  read-create
    STATUS      current
    DESCRIPTION
        "The LowReceivedPowerThreshold parameter indicates the power 
        level threshold to generate an event whenever the station 
        received power is below the threshold. The value -100 indicates 
        no threshold is set, and events of this type are not generated."
    DEFVAL      { -100 }
    ::= {clabWIFISSIDPolicyEntry 9 }

clabWIFISSIDPolicyLowPowerDeniedAccessThreshold    OBJECT-TYPE
    SYNTAX      Integer32 
    UNITS       "dBm"
    MAX-ACCESS  read-create
    STATUS      current
    DESCRIPTION
        "The LowPowerDeniedAccessThreshold parameter indicates the 
        power level threshold to deny client association whenever the 
        station received power is below the threshold. The value -100 
        indicates no threshold, and events of this type are not 
        generated."
    DEFVAL      { -100 }
    ::= {clabWIFISSIDPolicyEntry 10 }

clabWIFISSIDPolicyLowPowerDissasociationThreshold    OBJECT-TYPE
    SYNTAX      Integer32 
    UNITS       "dBm"
    MAX-ACCESS  read-create
    STATUS      current
    DESCRIPTION
        "The LowerPowerDissasociationThreshold parameter indicates 
        the threshold to report Disassociation due to low power. 
        The Wi-Fi GW should refuse associations when the power level 
        is below this RSSI level. The value -100 indicates no 
        threshold, and events of this type are not generated."
    DEFVAL      { -100 }
    ::= {clabWIFISSIDPolicyEntry 11 }
    
clabWIFISSIDPolicyRowStatus    OBJECT-TYPE
    SYNTAX      RowStatus 
    MAX-ACCESS  read-create
    STATUS      current
    DESCRIPTION
        "The status of this instance."
    ::= {clabWIFISSIDPolicyEntry 12 }     

clabWIFIClientSessionsTable OBJECT-TYPE
    SYNTAX      SEQUENCE OF ClabWIFIClientSessionsEntry
    MAX-ACCESS  not-accessible
    STATUS      current
    DESCRIPTION
        "The ClientSessions object represents the current 
        and closed sessions (association connections). 
        When the maximum number of instances is reached, the oldest 
        closed session instance is replaced by a newly created client 
        association."
    ::= {clabWIFIObjects 13 }

clabWIFIClientSessionsEntry    OBJECT-TYPE
    SYNTAX      ClabWIFIClientSessionsEntry
    MAX-ACCESS  not-accessible
    STATUS      current
    DESCRIPTION
        "The Conceptual row of clabWIFIClientSessionsTable."
    INDEX {
            clabWIFIAccessPointId, clabWIFIClientSessionsId
          }
    ::= {clabWIFIClientSessionsTable 1 }

ClabWIFIClientSessionsEntry ::= SEQUENCE {
    clabWIFIClientSessionsId
                 Unsigned32,
    clabWIFIClientSessionsDeviceMACAddress
                 MacAddress,
    clabWIFIClientSessionsStart
                 DateAndTime,
    clabWIFIClientSessionsStop
                 DateAndTime,
    clabWIFIClientSessionsTerminationCode
                 Unsigned32,
    clabWIFIClientSessionsTerminationMeaning
                 SnmpAdminString
      }

clabWIFIClientSessionsId    OBJECT-TYPE
    SYNTAX      Unsigned32 
    MAX-ACCESS  not-accessible
    STATUS      current
    DESCRIPTION
        "The Id key identifies a single client  MAC Address."
    ::= {clabWIFIClientSessionsEntry 1 }

clabWIFIClientSessionsDeviceMACAddress    OBJECT-TYPE
    SYNTAX      MacAddress 
    MAX-ACCESS  read-only
    STATUS      current
    DESCRIPTION
        "The DeviceMACAddress parameter indicates the MAC address 
        of an associated client device."
    ::= {clabWIFIClientSessionsEntry 2 }

clabWIFIClientSessionsStart    OBJECT-TYPE
    SYNTAX      DateAndTime 
    MAX-ACCESS  read-only
    STATUS      current
    DESCRIPTION
        "The Start parameter indicates the time when the session 
        started."
    ::= {clabWIFIClientSessionsEntry 3 }

clabWIFIClientSessionsStop    OBJECT-TYPE
    SYNTAX      DateAndTime 
    MAX-ACCESS  read-only
    STATUS      current
    DESCRIPTION
        "The Stop parameter indicates the time when the session ended. 
        If the session us current the value reported is all zeros."
    ::= {clabWIFIClientSessionsEntry 4 }

clabWIFIClientSessionsTerminationCode    OBJECT-TYPE
    SYNTAX      Unsigned32 
    MAX-ACCESS  read-only
    STATUS      current
    DESCRIPTION
        "The TerminationCode parameter indicates the Reason Code or the 
        Status Code that lead to ending the association of the station. 
        Reason code and Status code overlaps. The context of the type of 
        termination is provided by the TerminationMeaning attribute.
        The value zero indicates the session is active."
    ::= {clabWIFIClientSessionsEntry 5 }

clabWIFIClientSessionsTerminationMeaning    OBJECT-TYPE
    SYNTAX      SnmpAdminString (SIZE(0..32))
    MAX-ACCESS  read-only
    STATUS      current
    DESCRIPTION
        "The TerminationMeaning parameter indicates the meaning of the 
        Reason Code or Status Code for the ended session.  
        The zero-length string is used when the instance corresponds 
        to an active session."
    ::= {clabWIFIClientSessionsEntry 6 }

clabWIFIClientStatsTable OBJECT-TYPE
    SYNTAX      SEQUENCE OF ClabWIFIClientStatsEntry
    MAX-ACCESS  not-accessible
    STATUS      current
    DESCRIPTION
        "The ClientStats object contains accumulative statistics 
        for each client station.
        A station is reported only after is associated for the 
        first time. "
    ::= {clabWIFIObjects 14 }

clabWIFIClientStatsEntry    OBJECT-TYPE
    SYNTAX      ClabWIFIClientStatsEntry
    MAX-ACCESS  not-accessible
    STATUS      current
    DESCRIPTION
        "The Conceptual row of clabWIFIClientStatsTable."
    INDEX {
            clabWIFIAccessPointId, 
            clabWIFIClientStatsInterval, 
            clabWIFIClientStatsId
          }
    ::= {clabWIFIClientStatsTable 1 }

ClabWIFIClientStatsEntry ::= SEQUENCE {
    clabWIFIClientStatsInterval
                 Unsigned32,
    clabWIFIClientStatsId
                 Unsigned32,
    clabWIFIClientStatsDeviceMACAddress
                 MacAddress,
    clabWIFIClientStatsFramesSent
                 Counter64,
    clabWIFIClientStatsDataFramesSentAck
                 Counter64,
    clabWIFIClientStatsDataFramesSentNoAck
                 Counter64,
    clabWIFIClientStatsDataFramesLost
                 Counter64,
    clabWIFIClientStatsFramesReceived
                 Counter64,
    clabWIFIClientStatsDataFramesReceived
                 Counter64,
    clabWIFIClientStatsDataFramesDuplicateReceived
                 Counter64,
    clabWIFIClientStatsProbesReceived
                 Counter32,
    clabWIFIClientStatsProbesRejected
                 Counter32,
    clabWIFIClientStatsRSSI
                 Integer32,
    clabWIFIClientStatsSNR
                 Integer32,
    clabWIFIClientStatsDisassociations
                 Counter32,
    clabWIFIClientStatsAuthenticationFailures
                 Counter32,
    clabWIFIClientStatsLastTimeAssociation
                 DateAndTime,
    clabWIFIClientStatsLastTimeDisassociation
                 DateAndTime
      }

clabWIFIClientStatsInterval    OBJECT-TYPE
    SYNTAX      Unsigned32 (0 | 34 |48 | 96 )
    MAX-ACCESS  not-accessible
    STATUS      current
    DESCRIPTION
        "The Interval parameter indicate the measurements were 
        accumulated.
        The interval of measurements is synchronized with the 
        wall clock
        The total number of intervals is based on a 24 hour period. 
        At an interval of 15 minutes 96 intervals (1..96)  are defined, 
        at 30 minutes, 48 intervals (1..48) and 24 intervals (1..24) 
        for 1 hour measurement interval.
        Devices with  no capable to report measurements per interval 
        will report the value 0 for the interval attribute."
    ::= {clabWIFIClientStatsEntry 1 }

clabWIFIClientStatsId    OBJECT-TYPE
    SYNTAX      Unsigned32 
    MAX-ACCESS  not-accessible
    STATUS      current
    DESCRIPTION
        "The Id key identifies a single client  MAC Address."
    ::= {clabWIFIClientStatsEntry 2 }

clabWIFIClientStatsDeviceMACAddress    OBJECT-TYPE
    SYNTAX      MacAddress 
    MAX-ACCESS  read-only
    STATUS      current
    DESCRIPTION
        "The DeviceMACAddress parameter indicates the MAC address of 
        an associated client device."
    ::= {clabWIFIClientStatsEntry 3 }

clabWIFIClientStatsFramesSent    OBJECT-TYPE
    SYNTAX      Counter64 
    UNITS       "frames"
    MAX-ACCESS  read-only
    STATUS      current
    DESCRIPTION
        "The FramesSent parameter indicates the total number of frames 
        transmitted out of the interface.
        For conventional 802.11 MAC (a,b,g) this counter corresponds 
        to the total of MSDUs (MAC Service Data Unit) being transmitted.
        For High Throughput transmissions this corresponds to the 
        A-MSDU (Aggregation MSDU)
        The value of this counter MAY be reset to zero when the CPE 
        is rebooted."
    ::= {clabWIFIClientStatsEntry 4 }

clabWIFIClientStatsDataFramesSentAck    OBJECT-TYPE
    SYNTAX      Counter64 
    UNITS       "frames"
    MAX-ACCESS  read-only
    STATUS      current
    DESCRIPTION
        "The DataFramesSentAck parameter indicates the total number of 
        MSDU frames marked as duplicates and non duplicates acknowledged.
        The value of this counter MAY be reset to zero when the CPE is 
        rebooted."
    ::= {clabWIFIClientStatsEntry 5 }

clabWIFIClientStatsDataFramesSentNoAck    OBJECT-TYPE
    SYNTAX      Counter64 
    UNITS       "frames"
    MAX-ACCESS  read-only
    STATUS      current
    DESCRIPTION
        "The DataFramesSentNoAck parameter indicates the total number of 
        MSDU frames retransmitted out of the interface 
        (i.e., marked as duplicate and non-duplicate) and not acknowledged 
        but not including those defined in dataFramesLost.
        The value of this counter MAY be reset to zero when the CPE is 
        rebooted."
    ::= {clabWIFIClientStatsEntry 6 }

clabWIFIClientStatsDataFramesLost    OBJECT-TYPE
    SYNTAX      Counter64 
    UNITS       "frames"
    MAX-ACCESS  read-only
    STATUS      current
    DESCRIPTION
        "The DataFramesLost parameter indicates the total number of 
        MSDU frames retransmitted out of the interface that where not 
        acknowledged and discarded for reaching max number of 
        retransmissions.
        The value of this counter MAY be reset to zero when the CPE is 
        rebooted."
    ::= {clabWIFIClientStatsEntry 7 }

clabWIFIClientStatsFramesReceived    OBJECT-TYPE
    SYNTAX      Counter64 
    UNITS       "frames"
    MAX-ACCESS  read-only
    STATUS      current
    DESCRIPTION
        "The FramesReceived parameter indicates the total number of 
        frames received by the interface.
        For conventional 802.11 MAC (a,b,g) this counter corresponds 
        to the total of MSDUs (MAC Service Data Unit) being transmitted.
        For High Throughput transmissions (n) this corresponds to 
        A-MSDUs (Aggregation MSDU) and MSDUs.
        The value of this counter MAY be reset to zero when the 
        CPE is rebooted."
    ::= {clabWIFIClientStatsEntry 8 }

clabWIFIClientStatsDataFramesReceived    OBJECT-TYPE
    SYNTAX      Counter64 
    UNITS       "frames"
    MAX-ACCESS  read-only
    STATUS      current
    DESCRIPTION
        "The DataFramesReceived parameter indicates the total number 
        of MSDU frames received and  marked as non-duplicates.
        The value of this counter MAY be reset to zero when the CPE 
        is rebooted."
    ::= {clabWIFIClientStatsEntry 9 }

clabWIFIClientStatsDataFramesDuplicateReceived    OBJECT-TYPE
    SYNTAX      Counter64 
    UNITS       "frames"
    MAX-ACCESS  read-only
    STATUS      current
    DESCRIPTION
        "The DataFramesDuplicateReceived parameter indicates the total 
        number of duplicated frames received on this interface.
        The value of this counter MAY be reset to zero when the 
        CPE is rebooted."
    ::= {clabWIFIClientStatsEntry 10 }

clabWIFIClientStatsProbesReceived    OBJECT-TYPE
    SYNTAX      Counter32 
    UNITS       "probes"
    MAX-ACCESS  read-only
    STATUS      current
    DESCRIPTION
        "The ProbesReceived parameter indicates the Total number of 
        probes received."
    ::= {clabWIFIClientStatsEntry 11 }

clabWIFIClientStatsProbesRejected    OBJECT-TYPE
    SYNTAX      Counter32 
    UNITS       "probes"
    MAX-ACCESS  read-only
    STATUS      current
    DESCRIPTION
        "The ProbesRejected parameter indicates the total number of 
        probes rejected."
    ::= {clabWIFIClientStatsEntry 12 }

clabWIFIClientStatsRSSI    OBJECT-TYPE
    SYNTAX      Integer32 
    UNITS       "dBm"
    MAX-ACCESS  read-only
    STATUS      current
    DESCRIPTION
        "The Received Signal Strength Indicator, RSSI, parameter is the 
        energy observed at the antenna receiver for a current 
        transmission."
    ::= {clabWIFIClientStatsEntry 13 }

clabWIFIClientStatsSNR    OBJECT-TYPE
    SYNTAX      Integer32 
    UNITS       "dB"
    MAX-ACCESS  read-only
    STATUS      current
    DESCRIPTION
        "The signal to Noise Ratio (SNR) parameter indicates the signal 
        strength received from a client compared to the noise received."
    ::= {clabWIFIClientStatsEntry 14 }

clabWIFIClientStatsDisassociations    OBJECT-TYPE
    SYNTAX      Counter32 
    UNITS       "disassociations"
    MAX-ACCESS  read-only
    STATUS      current
    DESCRIPTION
        "The Disassociations parameter indicates the total number of 
        client disassociations."
    ::= {clabWIFIClientStatsEntry 15 }

clabWIFIClientStatsAuthenticationFailures    OBJECT-TYPE
    SYNTAX      Counter32 
    UNITS       "authenticationfailures"
    MAX-ACCESS  read-only
    STATUS      current
    DESCRIPTION
        "The AuthenticationFailures parameter indicates the total 
        number of authentication failures."
    ::= {clabWIFIClientStatsEntry 16 }

clabWIFIClientStatsLastTimeAssociation    OBJECT-TYPE
    SYNTAX      DateAndTime 
    MAX-ACCESS  read-only
    STATUS      current
    DESCRIPTION
        "The LastTimeAssociation parameter indicates the Last time 
        the client was associated."
    ::= {clabWIFIClientStatsEntry 17 }

clabWIFIClientStatsLastTimeDisassociation    OBJECT-TYPE
    SYNTAX      DateAndTime 
    MAX-ACCESS  read-only
    STATUS      current
    DESCRIPTION
        "The  LastTimeDisassociation parameter indicates the last time 
        the client disassociate from the interface. 
        The all zeros value indicates the client is currently 
        associated. "
    ::= {clabWIFIClientStatsEntry 18 }

clabWIFIRadiusClientTable OBJECT-TYPE
    SYNTAX      SEQUENCE OF ClabWIFIRadiusClientEntry
    MAX-ACCESS  not-accessible
    STATUS      current
    DESCRIPTION
        "This object is the extension of Radius Client operation
        for the Access Point 802.1x Authenticator for WPA Enterprise. 
        An instance is relevant when the attribute 
        AccessPointSecurity.ModeEnabled is 'WPA-Enterprise' or
        'WPA2-Enterprise' or 'WPA-WPA2-Enterprise'."
    ::= {clabWIFIObjects 15 }

clabWIFIRadiusClientEntry    OBJECT-TYPE
    SYNTAX      ClabWIFIRadiusClientEntry
    MAX-ACCESS  not-accessible
    STATUS      current
    DESCRIPTION
        "The Conceptual row of clabWIFIRadiusClientTable."
    INDEX {
            clabWIFIAccessPointId
          }
    ::= {clabWIFIRadiusClientTable 1 }

ClabWIFIRadiusClientEntry ::= SEQUENCE {
    clabWIFIRadiusClientNAS-Identifier
                 SnmpAdminString,
     clabWIFIRadiusClientLocationPolicy
                 OCTET STRING,
    clabWIFIRadiusClientOperatorName
                 SnmpAdminString,
    clabWIFIRadiusClientLocationInformation
                 OCTET STRING,
    clabWIFIRadiusClientLocationData
                 OCTET STRING,
    clabWIFIRadiusClientUsageReports
                 TruthValue,
    clabWIFIRadiusClientIntervalInterimReport
                 TruthValue,
    clabWIFIRadiusClientAPTransitionReport
                 TruthValue,
    clabWIFIRadiusClientGigawordReport
                 TruthValue,
    clabWIFIRadiusClientRowStatus
                 RowStatus
      }

clabWIFIRadiusClientNAS-Identifier    OBJECT-TYPE
    SYNTAX      SnmpAdminString (SIZE(0..255))
    MAX-ACCESS  read-create
    STATUS      current
    DESCRIPTION
        "The NAS-Identifier parameter corresponds to the Radius 
        attribute NAS-Identifier used in Access request messages.
        The device always sends the Radius parameter NAS-IP-Address
        and will send the NAS-Identifier parameter when this 
        attribute is set to other than the zero-length string. 
        The NAS-Identifier attribute can be used as a hint to 
        indicate the authentication server the SSID domain where 
        the WiFi endpoint tries to authenticate, i.e., 
        when more than one SSID domains are using the same 
        Radius server instance."
    ::= {clabWIFIRadiusClientEntry 1 }

clabWIFIRadiusClientLocationPolicy    OBJECT-TYPE
    SYNTAX      OCTET STRING (SIZE(0..64)) 
    MAX-ACCESS  read-create
    STATUS      current
    DESCRIPTION
        "The LocationPolicy  corresponds to the string value of the 
        Radius Basic-Location-Policy-Rules attribute per RFC 5580"
    ::= {clabWIFIRadiusClientEntry 2 }

clabWIFIRadiusClientOperatorName    OBJECT-TYPE
    SYNTAX      SnmpAdminString (SIZE(0..32)) 
    MAX-ACCESS  read-create
    STATUS      current
    DESCRIPTION
        "The OperatorName parameter corresponds to the string value of the 
        Radius Operator-Name attribute per RFC 5580."
    ::= {clabWIFIRadiusClientEntry 3 }

clabWIFIRadiusClientLocationInformation    OBJECT-TYPE
    SYNTAX      OCTET STRING (SIZE(0..253)) 
    MAX-ACCESS  read-create
    STATUS      current
    DESCRIPTION
        "The LocationInformation parameter corresponds to the string 
        value of the Radius Location-Information  attribute per 
        RFC 5580."
    ::= {clabWIFIRadiusClientEntry 4 }

clabWIFIRadiusClientLocationData    OBJECT-TYPE
    SYNTAX      OCTET STRING (SIZE(0..253)) 
    MAX-ACCESS  read-create
    STATUS      current
    DESCRIPTION
        "The Location Data parameter corresponds to the string value of 
        the Radius LocationData attribute per RFC 5580."
    ::= {clabWIFIRadiusClientEntry 5 }

clabWIFIRadiusClientUsageReports    OBJECT-TYPE
    SYNTAX      TruthValue 
    MAX-ACCESS  read-create
    STATUS      current
    DESCRIPTION
        "The UsageReports parameter indicates whether the client send 
        usage data 'true' or not 'false'."
    DEFVAL      { false }
    ::= {clabWIFIRadiusClientEntry 6 }

clabWIFIRadiusClientIntervalInterimReport    OBJECT-TYPE
    SYNTAX      TruthValue 
    MAX-ACCESS  read-create
    STATUS      current
    DESCRIPTION
        "The IntervalInterimReport parameter indicates whether the client 
        send Interim reports at time intervals 'true' or not 'false'."
    DEFVAL      { false }
    ::= {clabWIFIRadiusClientEntry 7 }

clabWIFIRadiusClientAPTransitionReport    OBJECT-TYPE
    SYNTAX      TruthValue 
    MAX-ACCESS  read-create
    STATUS      current
    DESCRIPTION
        "A 'true' value for the APTransitionReport parameter indicates the 
        client sends Interim reports when the stations transitions to a 
        different Access point."
    DEFVAL      { false }
    ::= {clabWIFIRadiusClientEntry 8 }

clabWIFIRadiusClientGigawordReport    OBJECT-TYPE
    SYNTAX      TruthValue 
    MAX-ACCESS  read-create
    STATUS      current
    DESCRIPTION
        "A 'true' value for Gigaword Report indicates the client sends 
        Interim reports when the 32-bit counters rollover"
    DEFVAL      { false }
    ::= {clabWIFIRadiusClientEntry 9 }

clabWIFIRadiusClientRowStatus    OBJECT-TYPE
    SYNTAX      RowStatus 
    MAX-ACCESS  read-create
    STATUS      current
    DESCRIPTION
        "The status of this instance."
    ::= {clabWIFIRadiusClientEntry 10 }

clabWIFIWIFIEventNotif NOTIFICATION-TYPE
    OBJECTS     { 
                  clabWIFIWIFIEventNotifText,
                  clabWIFIWIFIEventNotifEventId,
                  clabWIFIWIFIEventNotifTimeStamp }
    STATUS      current
    DESCRIPTION
        "This object represents the Wi-Fi GW notification."
  ::= {clabWIFINotifications 1 }

clabWIFIWIFIEventNotifgroup OBJECT IDENTIFIER ::= { clabWIFINotifications 2} 


clabWIFIWIFIEventNotifText    OBJECT-TYPE
    SYNTAX      SnmpAdminString 
    MAX-ACCESS  accessible-for-notify
    STATUS      current
    DESCRIPTION
        "This attribute represents the Event Message of the event."
    ::= {clabWIFIWIFIEventNotifgroup 1 }

clabWIFIWIFIEventNotifEventId    OBJECT-TYPE
    SYNTAX      Unsigned32 
    MAX-ACCESS  accessible-for-notify
    STATUS      current
    DESCRIPTION
        "The identifier of the event"
    ::= {clabWIFIWIFIEventNotifgroup 2 }

clabWIFIWIFIEventNotifTimeStamp    OBJECT-TYPE
    SYNTAX      DateAndTime
    MAX-ACCESS  accessible-for-notify
    STATUS      current
    DESCRIPTION
        "Date and Time when the event was generated. (not the time when 
        the event was dispatched)."
    ::= {clabWIFIWIFIEventNotifgroup 3 }


-- Conformance Definitions
		clabWIFIMibConformance OBJECT IDENTIFIER ::= { clabWIFIMib 2 }
clabWIFIMibCompliances OBJECT IDENTIFIER ::= { clabWIFIMibConformance 1 }
clabWIFIMibGroups      OBJECT IDENTIFIER ::= { clabWIFIMibConformance 2 }

clabWIFICompliance MODULE-COMPLIANCE
    STATUS      current
    DESCRIPTION
         "The compliance statement for the."
    MODULE -- this MODULE
    MANDATORY-GROUPS {
            clabWIFIGroup, clabWIFINotificationsGroup
            }
    ::= { clabWIFIMibCompliances 1 }

clabWIFIGroup OBJECT-GROUP
    OBJECTS {
              clabWIFIAccessPointEnable,
              clabWIFIAccessPointStatus,
              clabWIFIAccessPointAlias,
              clabWIFIAccessPointSSIDReference,
              clabWIFIAccessPointSSIDAdvertisementEnabled,
              clabWIFIAccessPointRetryLimit,
              clabWIFIAccessPointWMMCapability,
              clabWIFIAccessPointUAPSDCapability,
              clabWIFIAccessPointWMMEnable,
              clabWIFIAccessPointUAPSDEnable,
              clabWIFIAccessPointAssociatedDeviceNumberOfEntries,
              clabWIFIAccessPointAssociatedDeviceRowStatus,
              clabWIFIAccessPointWPSEnable,
              clabWIFIAccessPointWPSConfigMethodsSupported,
              clabWIFIAccessPointWPSConfigMethodsEnabled,
              clabWIFIAccessPointWPSRowStatus,
              clabWIFIRadiusClientNAS-Identifier,
              clabWIFIRadiusClientLocationPolicy,
              clabWIFIRadiusClientOperatorName,
              clabWIFIRadiusClientLocationInformation,
              clabWIFIRadiusClientLocationData,
              clabWIFIRadiusClientUsageReports,
              clabWIFIRadiusClientIntervalInterimReport,
              clabWIFIRadiusClientAPTransitionReport,
              clabWIFIRadiusClientGigawordReport,
              clabWIFIRadiusClientRowStatus,
              clabWIFISSIDEnable,
              clabWIFISSIDStatus,
              clabWIFISSIDAlias,
              clabWIFISSIDName,
              clabWIFISSIDLastChange,
              clabWIFISSIDLowerLayers,
              clabWIFISSIDBSSID,
              clabWIFISSIDMACAddress,
              clabWIFISSIDSSID,
              clabWIFISSIDRowStatus,
              clabWIFIAssociatedDeviceMACAddress,
              clabWIFIAssociatedDeviceAuthenticationState,
              clabWIFIAssociatedDeviceLastDataDownlinkRate,
              clabWIFIAssociatedDeviceLastDataUplinkRate,
              clabWIFIAssociatedDeviceSignalStrength,
              clabWIFIAssociatedDeviceRetransmissions,
              clabWIFIAssociatedDeviceActive,
              clabWIFIClientSessionsDeviceMACAddress,
              clabWIFIClientSessionsStart,
              clabWIFIClientSessionsStop,
              clabWIFIClientSessionsTerminationCode,
              clabWIFIClientSessionsTerminationMeaning,
              clabWIFIRadioStatsBytesSent,
              clabWIFIRadioStatsBytesReceived,
              clabWIFIRadioStatsPacketsSent,
              clabWIFIRadioStatsPacketsReceived,
              clabWIFIRadioStatsErrorsSent,
              clabWIFIRadioStatsErrorsReceived,
              clabWIFIRadioStatsDiscardPacketsSent,
              clabWIFIRadioStatsDiscardPacketsReceived,
              clabWIFISSIDStatsBytesSent,
              clabWIFISSIDStatsBytesReceived,
              clabWIFISSIDStatsPacketsSent,
              clabWIFISSIDStatsPacketsReceived,
              clabWIFISSIDStatsErrorsSent,
              clabWIFISSIDStatsErrorsReceived,
              clabWIFISSIDStatsUnicastPacketsSent,
              clabWIFISSIDStatsUnicastPacketsReceived,
              clabWIFISSIDStatsDiscardPacketsSent,
              clabWIFISSIDStatsDiscardPacketsReceived,
              clabWIFISSIDStatsMulticastPacketsSent,
              clabWIFISSIDStatsMulticastPacketsReceived,
              clabWIFISSIDStatsBroadcastPacketsSent,
              clabWIFISSIDStatsBroadcastPacketsReceived,
              clabWIFISSIDStatsUnknownProtoPacketsReceived,
              clabWIFIPeriodicStatsDeviceMACAddress,
              clabWIFIPeriodicStatsFramesSent,
              clabWIFIPeriodicStatsDataFramesSentAck,
              clabWIFIPeriodicStatsDataFramesSentNoAck,
              clabWIFIPeriodicStatsDataFramesLost,
              clabWIFIPeriodicStatsFramesReceived,
              clabWIFIPeriodicStatsDataFramesReceived,
              clabWIFIPeriodicStatsDataFramesDuplicateReceived,
              clabWIFIPeriodicStatsProbesReceived,
              clabWIFIPeriodicStatsProbesRejected,
              clabWIFIPeriodicStatsRSSI,
              clabWIFIPeriodicStatsSNR,
              clabWIFIPeriodicStatsDisassociations,
              clabWIFIPeriodicStatsAuthenticationFailures,
              clabWIFIPeriodicStatsLastTimeAssociation,
              clabWIFIPeriodicStatsLastTimeDisassociation,
              clabWIFIClientStatsDeviceMACAddress,
              clabWIFIClientStatsFramesSent,
              clabWIFIClientStatsDataFramesSentAck,
              clabWIFIClientStatsDataFramesSentNoAck,
              clabWIFIClientStatsDataFramesLost,
              clabWIFIClientStatsFramesReceived,
              clabWIFIClientStatsDataFramesReceived,
              clabWIFIClientStatsDataFramesDuplicateReceived,
              clabWIFIClientStatsProbesReceived,
              clabWIFIClientStatsProbesRejected,
              clabWIFIClientStatsRSSI,
              clabWIFIClientStatsSNR,
              clabWIFIClientStatsDisassociations,
              clabWIFIClientStatsAuthenticationFailures,
              clabWIFIClientStatsLastTimeAssociation,
              clabWIFIClientStatsLastTimeDisassociation,
              clabWIFIRadioEnable,
              clabWIFIRadioStatus,
              clabWIFIRadioAlias,
              clabWIFIRadioName,
              clabWIFIRadioLastChange,
              clabWIFIRadioLowerLayers,
              clabWIFIRadioUpstream,
              clabWIFIRadioMaxBitRate,
              clabWIFIRadioSupportedFrequencyBands,
              clabWIFIRadioOperatingFrequencyBand,
              clabWIFIRadioSupportedStandards,
              clabWIFIRadioOperatingStandards,
              clabWIFIRadioPossibleChannels,
              clabWIFIRadioChannelsInUse,
              clabWIFIRadioChannel,
              clabWIFIRadioAutoChannelSupported,
              clabWIFIRadioAutoChannelEnable,
              clabWIFIRadioAutoChannelRefreshPeriod,
              clabWIFIRadioOperatingChannelBandwidth,
              clabWIFIRadioExtensionChannel,
              clabWIFIRadioGuardInterval,
              clabWIFIRadioMCS,
              clabWIFIRadioTransmitPowerSupported,
              clabWIFIRadioTransmitPower,
              clabWIFIRadioIEEE80211hSupported,
              clabWIFIRadioIEEE80211hEnabled,
              clabWIFIRadioRegulatoryDomain,
              clabWIFIWiFiRadioNumberOfEntries,
              clabWIFIWiFiSSIDNumberOfEntries,
              clabWIFIWiFiAccessPointNumberOfEntries,
              clabWIFIWiFiEndPointNumberOfEntries,
              clabWIFIDataRateStatsFramesSent,
              clabWIFIDataRateStatsFramesRetransmissionsSent,
              clabWIFIDataRateStatsFramesReceived,
              clabWIFIDataRateStatsFramesDuplicatedReceived,
              clabWIFIWIFIEventNotifText,
              clabWIFIWIFIEventNotifEventId,
              clabWIFIWIFIEventNotifTimeStamp,
              clabWIFIAccessPointSecurityModesSupported,
              clabWIFIAccessPointSecurityModeEnabled,
              clabWIFIAccessPointSecurityWEPKey,
              clabWIFIAccessPointSecurityPreSharedKey,
              clabWIFIAccessPointSecurityKeyPassphrase,
              clabWIFIAccessPointSecurityRekeyingInterval,
              clabWIFIAccessPointSecurityRadiusServerIPAddrType,
              clabWIFIAccessPointSecurityRadiusServerIPAddr,
              clabWIFIAccessPointSecurityRadiusServerPort,
              clabWIFIAccessPointSecurityRadiusSecret,
              clabWIFIAccessPointSecurityRowstatus,
              clabWIFISSIDPolicyBlockAfterAttempts,
              clabWIFISSIDPolicyAllocatedBandwidth,
              clabWIFISSIDPolicyAuthenticationFailures,
              clabWIFISSIDPolicyNonAuthenticatedTraffic,
              clabWIFISSIDPolicyAssociationFailures,
              clabWIFISSIDPolicyStatsInterval,
              clabWIFISSIDPolicySNRThreshold,
              clabWIFISSIDPolicyANPIThreshold,
              clabWIFISSIDPolicyLowReceivedPowerThreshold,
              clabWIFISSIDPolicyLowPowerDeniedAccessThreshold,
              clabWIFISSIDPolicyLowPowerDissasociationThreshold,
              clabWIFISSIDPolicyRowStatus
    }
    STATUS      current
    DESCRIPTION
             "Objects implemented in the clabWIFIGroup."
    ::= { clabWIFIMibGroups 1 }

clabWIFINotificationsGroup NOTIFICATION-GROUP
   NOTIFICATIONS { clabWIFIWIFIEventNotif }
   STATUS        current
   DESCRIPTION
           "Notifications implemented in the clabWIFINotificationsGroup."
   ::= { clabWIFIMibGroups 2 }

END
